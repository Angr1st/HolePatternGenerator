# -*- coding: utf-8 -*-

# Macro Begin: 
import FreeCAD
import PartDesign
import PartDesignGui
import Sketcher
from enum import Enum

HoleType = Enum('HoleType', ['CENTER', 'RIGHTTOP', 'RIGHTBOTTOM', 'LEFTBOTTOM', 'LEFTTOP', 'TOP', 'RIGHT', 'BOTTOM', 'LEFT'])

documentName = 'unifilter_lellit_anna_57mm_hole_pattern_v2'

document = App.getDocument(documentName)

def formatAs(unit,number):
    return f'{number} {unit}'

def formatAsDeg(number):
    return formatAs('deg', number)

def formatAsMM(number):
    return formatAs('mm', number)

class HoleDefinition:
    def __init__(self, totalDepth, innerDiameter, straightDepth, holeAngle):
        self.totalDepth = totalDepth
        self.innerDiameter = innerDiameter
        self.straightDepth = straightDepth
        self.holeAngle = holeAngle
        self.innerRadius = innerDiameter / 2.0

    def OutputHoleAngle(self):
        return formatAsDeg(self.holeAngle)

    def OutputInnerRadius(self):
        return formatAsMM(self.innerRadius)

    def OutputTotalDepth(self):
        return formatAsMM(self.totalDepth)

    def OutputStraigthDepth(self):
        return formatAsMM(self.straightDepth)

    def OutputInnerDiameter(self):
        return formatAsMM(self.innerDiameter)

class HolePosition:
    def __init__(self, x, z, holeType):
        self.X = x
        self.Z = z
        self.HolePositionType = holeType

    def OutputX(self):
        return formatAsMM(self.X)

    def OutputZ(self):
        return formatAsMM(self.Z)

class HolePlaneIterator:
    def __init__(self):
        self.ObjectNumber = 0
        self.ConstraintNumber = 0

def generateSketchName(number):
    return f'Sketch{number:03d}'

def generateGrooveName(number):
    return f'Groove{number:03d}'

def createSketch(number):
    sketchName = generateSketchName(number)

    document.getObject('Body').newObject('Sketcher::SketchObject',sketchName)

    return document.getObject(sketchName)

def paintHolePlane(sketch, definition, holes):
    sketch.Support = (document.getObject('XY_Plane'),[''])
    sketch.MapMode = 'FlatFace'
    
    hpi = HolePlaneIterator()
    #Complete Plane
    sketch.addGeometry(Part.Circle(App.Vector(0.000000,0.000000,0),App.Vector(0,0,1),0.998513),False)
    sketch.addConstraint(Sketcher.Constraint('Coincident',hpi.ObjectNumber,3,-1,1)) 
    hpi.ConstraintNumber += 1
    sketch.addConstraint(Sketcher.Constraint('Diameter',hpi.ObjectNumber,1.997026))
    sketch.setDatum(hpi.ConstraintNumber,App.Units.Quantity('58.100000 mm'))
    hpi.ObjectNumber += 1

    def createCenterHole(hpit):
        # Center Hole
        sketch.addGeometry(Part.Circle(App.Vector(0.000000,0.000000,0),App.Vector(0,0,1),0.719121),False)
        hpit.ConstraintNumber += 1
        sketch.addConstraint(Sketcher.Constraint('Coincident',hpit.ObjectNumber,3,0,3)) 
        hpit.ConstraintNumber += 1
        sketch.addConstraint(Sketcher.Constraint('Diameter',hpit.ObjectNumber,1.438242)) 
        sketch.setDatum(hpit.ConstraintNumber,App.Units.Quantity(definition.OutputInnerDiameter()))

    def createHoleLeft(hpit,hole):
        sketch.addGeometry(Part.Circle(App.Vector(-0.903611,0.001554,0),App.Vector(0,0,1),0.104209),False)
        hpit.ConstraintNumber += 1
        sketch.addConstraint(Sketcher.Constraint('PointOnObject',hpit.ObjectNumber,3,-1)) 
        hpit.ConstraintNumber += 1
        sketch.addConstraint(Sketcher.Constraint('Diameter',hpit.ObjectNumber,0.208418)) 
        sketch.setDatum(hpit.ConstraintNumber,App.Units.Quantity(definition.OutputInnerDiameter()))
        hpit.ConstraintNumber += 1
        sketch.addConstraint(Sketcher.Constraint('DistanceX',hpit.ObjectNumber,3,0,3,0.903611)) 
        sketch.setDatum(hpit.ConstraintNumber,App.Units.Quantity(hole.OutputZ()))
        #sketch.renameConstraint(6, u'Left')

    def createHoleLeftTop(hpit,hole):
        sketch.addGeometry(Part.Circle(App.Vector(-0.647308,0.643353,0),App.Vector(0,0,1),0.140588),False)
        hpit.ConstraintNumber += 1
        sketch.addConstraint(Sketcher.Constraint('Diameter',hpit.ObjectNumber,0.281176)) 
        sketch.setDatum(hpit.ConstraintNumber,App.Units.Quantity(definition.OutputInnerDiameter()))
        hpit.ConstraintNumber += 1
        sketch.addConstraint(Sketcher.Constraint('DistanceX',hpit.ObjectNumber,3,0,3,0.647308)) 
        sketch.setDatum(hpit.ConstraintNumber,App.Units.Quantity(hole.OutputZ()))
        hpit.ConstraintNumber += 1
        sketch.addConstraint(Sketcher.Constraint('DistanceY',0,3,hpit.ObjectNumber,3,0.643353)) 
        sketch.setDatum(hpit.ConstraintNumber,App.Units.Quantity(hole.OutputX()))

    def createHoleTop(hpit,hole):
        sketch.addGeometry(Part.Circle(App.Vector(-0.006343,1.042262,0),App.Vector(0,0,1),0.179877),False)
        hpit.ConstraintNumber += 1
        sketch.addConstraint(Sketcher.Constraint('PointOnObject',hpit.ObjectNumber,3,-2)) 
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',0,3,hpit.ObjectNumber,3,1.042262)) 
        sketch.setDatum(hpit.ConstraintNumber,App.Units.Quantity(hole.OutputX()))
        #sketch.renameConstraint(12, u'Top')

    def createHoleRightTop(hpit,hole):
        sketch.addGeometry(Part.Circle(App.Vector(1.017571,0.952324,0),App.Vector(0,0,1),0.245674),False)
        hpit.ConstraintNumber += 1
        sketch.addConstraint(Sketcher.Constraint('Diameter',hpit.ObjectNumber,0.491348)) 
        sketch.setDatum(hpit.ConstraintNumber,App.Units.Quantity(definition.OutputInnerDiameter()))
        hpit.ConstraintNumber += 1
        sketch.addConstraint(Sketcher.Constraint('DistanceX',0,3,hpit.ObjectNumber,3,1.017571)) 
        sketch.setDatum(hpit.ConstraintNumber,App.Units.Quantity(hole.OutputZ()))
        hpit.ConstraintNumber += 1
        sketch.addConstraint(Sketcher.Constraint('DistanceY',0,3,hpit.ObjectNumber,3,0.952324)) 
        sketch.setDatum(hpit.ConstraintNumber,App.Units.Quantity(hole.OutputX()))

    def createHoleRight(hpit,hole):
        sketch.addGeometry(Part.Circle(App.Vector(0.976061,-0.016243,0),App.Vector(0,0,1),0.271319),False)
        hpit.ConstraintNumber += 1
        sketch.addConstraint(Sketcher.Constraint('PointOnObject',hpit.ObjectNumber,3,-1)) 
        hpit.ConstraintNumber += 1
        sketch.addConstraint(Sketcher.Constraint('Diameter',hpit.ObjectNumber,0.542638)) 
        sketch.setDatum(hpit.ConstraintNumber,App.Units.Quantity(definition.OutputInnerDiameter()))
        hpit.ConstraintNumber += 1
        sketch.addConstraint(Sketcher.Constraint('DistanceX',0,3,hpit.ObjectNumber,3,0.976061)) 
        sketch.setDatum(hpit.ConstraintNumber,App.Units.Quantity(hole.OutputZ()))
        #sketch.renameConstraint(18, u'Right')

    def createHoleRightBottom(hpit,hole):
        sketch.addGeometry(Part.Circle(App.Vector(0.982979,-0.957137,0),App.Vector(0,0,1),0.179877),False)
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',hpit.ObjectNumber,3,0,3,0.957137)) 
        sketch.setDatum(hpit.ConstraintNumber,App.Units.Quantity(hole.OutputX()))
        hpit.ConstraintNumber += 1
        sketch.addConstraint(Sketcher.Constraint('DistanceX',0,3,hpit.ObjectNumber,3,0.982979)) 
        sketch.setDatum(hpit.ConstraintNumber,App.Units.Quantity(hole.OutputZ()))

    def createHoleBottom(hpit,hole):
        sketch.addGeometry(Part.Circle(App.Vector(-0.006343,-1.012484,0),App.Vector(0,0,1),0.196899),False)
        hpit.ConstraintNumber += 1
        sketch.addConstraint(Sketcher.Constraint('PointOnObject',hpit.ObjectNumber,3,-2)) 
        hpit.ConstraintNumber += 1
        sketch.addConstraint(Sketcher.Constraint('Diameter',hpit.ObjectNumber,0.393798)) 
        sketch.setDatum(hpit.ConstraintNumber,App.Units.Quantity(definition.OutputInnerDiameter()))
        hpit.ConstraintNumber += 1
        sketch.addConstraint(Sketcher.Constraint('DistanceY',hpit.ObjectNumber,3,0,3,1.012484)) 
        sketch.setDatum(hpit.ConstraintNumber,App.Units.Quantity(hole.OutputX()))

    def createHoleLeftBottom(hpit,hole):
        sketch.addGeometry(Part.Circle(App.Vector(-1.044094,-0.991729,0),App.Vector(0,0,1),0.179877),False)
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',hpit.ObjectNumber,3,0,3,0.991729)) 
        sketch.setDatum(hpit.ConstraintNumber,App.Units.Quantity(hole.OutputX()))
        hpit.ConstraintNumber += 1
        sketch.addConstraint(Sketcher.Constraint('DistanceX',hpit.ObjectNumber,3,0,3,1.044094)) 
        sketch.setDatum(hpit.ConstraintNumber,App.Units.Quantity(hole.OutputZ()))

    for hole in holes:
        if hole.HolePositionType == HoleType.CENTER:
            createCenterHole(hpi)
        elif hole.HolePositionType == HoleType.RIGHTTOP:
            createHoleRightTop(hpi,hole)
        elif hole.HolePositionType == HoleType.RIGHTBOTTOM:
            createHoleRightBottom(hpi,hole)
        elif hole.HolePositionType == HoleType.LEFTBOTTOM:
            createHoleLeftBottom(hpi,hole)
        elif hole.HolePositionType == HoleType.LEFTTOP:
            createHoleLeftTop(hpi,hole)
        elif hole.HolePositionType == HoleType.TOP:
            createHoleTop(hpi,hole)
        elif hole.HolePositionType == HoleType.RIGHT:
            createHoleRight(hpi,hole)
        elif hole.HolePositionType == HoleType.BOTTOM:
            createHoleBottom(hpi,hole)
        elif hole.HolePositionType == HoleType.LEFT:
            createHoleLeft(hpi,hole)
        
        hpi.ObjectNumber += 1

def paintSketch(sketch, definition, position):
    sketch.Support = (document.getObject('XZ_Plane'),[''])
    sketch.MapMode = 'FlatFace'

    sketch.addGeometry(Part.LineSegment(App.Vector(0.000000,-0.000000,0),App.Vector(-0.001979,1.008049,0)),False)
    sketch.addConstraint(Sketcher.Constraint('Coincident',0,1,-1,1)) 
    sketch.addConstraint(Sketcher.Constraint('PointOnObject',0,2,-2)) 

    sketch.addConstraint(Sketcher.Constraint('DistanceY',0,1,0,2,1.008049)) 
    sketch.setDatum(2,App.Units.Quantity(definition.OutputTotalDepth()))

    sketch.addGeometry(Part.LineSegment(App.Vector(0.000000,1.000000,0),App.Vector(-0.223077,1.008049,0)),False)
    sketch.addConstraint(Sketcher.Constraint('Coincident',1,1,0,2)) 
    sketch.movePoint(1,2,App.Vector(-0.220129,1.002153,0),0)

    sketch.addConstraint(Sketcher.Constraint('Horizontal',1))

    sketch.addConstraint(Sketcher.Constraint('DistanceX',1,2,1,1,0.220129)) 

    sketch.setDatum(5,App.Units.Quantity(definition.OutputInnerRadius()))

    sketch.addGeometry(Part.LineSegment(App.Vector(-0.150000,1.000000,0),App.Vector(-0.139617,0.158150,0)),False)
    sketch.addConstraint(Sketcher.Constraint('Coincident',2,1,1,2)) 
    sketch.addConstraint(Sketcher.Constraint('Vertical',2)) 

    sketch.addConstraint(Sketcher.Constraint('DistanceY',2,2,2,1,0.841850)) 
    sketch.setDatum(8,App.Units.Quantity(definition.OutputStraigthDepth()))

    sketch.addGeometry(Part.LineSegment(App.Vector(-0.150000,0.250000,0),App.Vector(-0.142565,-0.001041,0)),True)
    sketch.addConstraint(Sketcher.Constraint('Coincident',3,1,2,2)) 
    sketch.addConstraint(Sketcher.Constraint('PointOnObject',3,2,-1)) 
    sketch.addConstraint(Sketcher.Constraint('Vertical',3)) 

    sketch.addGeometry(Part.LineSegment(App.Vector(-0.150000,0.250000,0),App.Vector(-0.272368,-0.003883,0)),False)
    sketch.addConstraint(Sketcher.Constraint('Coincident',4,1,2,2)) 
    sketch.addConstraint(Sketcher.Constraint('PointOnObject',4,2,-1)) 

    sketch.addConstraint(Sketcher.Constraint('Angle',4,1,3,1,0.455190)) 
    sketch.setDatum(14,App.Units.Quantity(definition.OutputHoleAngle()))

    sketch.addGeometry(Part.LineSegment(App.Vector(-0.266577,-0.000000,0),App.Vector(0.000000,-0.000000,0)),False)
    sketch.addConstraint(Sketcher.Constraint('Coincident',5,1,4,2)) 
    sketch.addConstraint(Sketcher.Constraint('Coincident',5,2,0,1)) 

    sketch.AttachmentOffset.Base.x = position.X
    sketch.AttachmentOffset.Base.z = position.Z

def createGroove(number):
    grooveName = generateGrooveName(number)

    document.getObject('Body').newObject('PartDesign::Groove',grooveName)

    return document.getObject(grooveName)

def paintGroove(sketch,groove):
    groove.Profile = sketch
    groove.ReferenceAxis = (sketch,['V_Axis'])
    groove.Angle = 360.0
    groove.Midplane = 0
    groove.Reversed = 0
    sketch.Visibility = False

def createHole(number, holeDefinition, holePosition):
    sketch = createSketch(number)

    paintSketch(sketch,holeDefinition,holePosition)

    groove = createGroove(number)

    paintGroove(sketch,groove)

holeList = []
