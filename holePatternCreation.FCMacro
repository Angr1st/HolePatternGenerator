# -*- coding: utf-8 -*-

# Macro Begin: 
import FreeCAD
import PartDesign
import PartDesignGui
import Sketcher
from enum import Enum

HoleType = Enum('HoleType', ['CENTER', 'RIGHTTOP', 'RIGHTBOTTOM', 'LEFTBOTTOM', 'LEFTTOP', 'TOP', 'RIGHT', 'BOTTOM', 'LEFT'])

documentName = 'unifilter_lellit_anna_57mm_hole_pattern_v2'

document = App.getDocument(documentName)

def formatAs(unit,number):
    return f'{number} {unit}'

def formatAsDeg(number):
    return formatAs('deg', number)

def formatAsMM(number):
    return formatAs('mm', number)

class HoleDefinition:
    def __init__(self, totalDepth, innerDiameter, straightDepth, holeAngle):
        self.totalDepth = totalDepth
        self.innerDiameter = innerDiameter
        self.straightDepth = straightDepth
        self.holeAngle = holeAngle
        self.innerRadius = innerDiameter / 2.0

    def OutputHoleAngle(self):
        return formatAsDeg(self.holeAngle)

    def OutputInnerRadius(self):
        return formatAsMM(self.innerRadius)

    def OutputTotalDepth(self):
        return formatAsMM(self.totalDepth)

    def OutputStraigthDepth(self):
        return formatAsMM(self.straightDepth)

    def OutputInnerDiameter(self):
        return formatAsMM(self.innerDiameter)

class HolePosition:
    def __init__(self, x, z, holeType):
        self.X = x
        self.Z = z
        self.HolePositionType = holeType

    def OutputX(self):
        return formatAsMM(self.X)

    def OutputZ(self):
        return formatAsMM(self.Z)

class HolePlaneIterator:
    def __init__(self):
        self.ObjectNumber = 0
        self.ConstraintNumber = 0

def generateSketchName(number):
    return f'Sketch{number:03d}'

def generateGrooveName(number):
    return f'Groove{number:03d}'

def createSketch(number):
    sketchName = generateSketchName(number)

    document.getObject('Body').newObject('Sketcher::SketchObject',sketchName)

    return document.getObject(sketchName)

def paintHolePlane(sketch, definition, holes):
    sketch.Support = (document.getObject('XY_Plane'),[''])
    sketch.MapMode = 'FlatFace'
    
    hpi = HolePlaneIterator()
    #Complete Plane
    sketch.addGeometry(Part.Circle(App.Vector(0.000000,0.000000,0),App.Vector(0,0,1),0.998513),False)
    sketch.addConstraint(Sketcher.Constraint('Coincident',hpi.ObjectNumber,3,-1,1)) 
    hpi.ConstraintNumber += 1
    sketch.addConstraint(Sketcher.Constraint('Diameter',hpi.ObjectNumber,1.997026))
    sketch.setDatum(hpi.ConstraintNumber,App.Units.Quantity('58.100000 mm'))
    hpi.ObjectNumber += 1

    def createCenterHole(hpit):
        # Center Hole
        sketch.addGeometry(Part.Circle(App.Vector(0.000000,0.000000,0),App.Vector(0,0,1),0.719121),False)
        hpit.ConstraintNumber += 1
        sketch.addConstraint(Sketcher.Constraint('Coincident',hpit.ObjectNumber,3,0,3)) 
        hpit.ConstraintNumber += 1
        sketch.addConstraint(Sketcher.Constraint('Diameter',hpit.ObjectNumber,1.438242)) 
        sketch.setDatum(hpit.ConstraintNumber,App.Units.Quantity(definition.OutputInnerDiameter()))

    def createHoleLeft(hpit,hole):
        sketch.addGeometry(Part.Circle(App.Vector(-0.903611,0.001554,0),App.Vector(0,0,1),0.104209),False)
        hpit.ConstraintNumber += 1
        sketch.addConstraint(Sketcher.Constraint('PointOnObject',hpit.ObjectNumber,3,-1)) 
        hpit.ConstraintNumber += 1
        sketch.addConstraint(Sketcher.Constraint('Diameter',hpit.ObjectNumber,0.208418)) 
        sketch.setDatum(hpit.ConstraintNumber,App.Units.Quantity(definition.OutputInnerDiameter()))
        hpit.ConstraintNumber += 1
        sketch.addConstraint(Sketcher.Constraint('DistanceX',hpit.ObjectNumber,3,0,3,0.903611)) 
        sketch.setDatum(hpit.ConstraintNumber,App.Units.Quantity(hole.OutputZ()))
        #sketch.renameConstraint(6, u'Left')

    def createHoleLeftTop(hpit,hole):
        sketch.addGeometry(Part.Circle(App.Vector(-0.647308,0.643353,0),App.Vector(0,0,1),0.140588),False)
        hpit.ConstraintNumber += 1
        sketch.addConstraint(Sketcher.Constraint('Diameter',hpit.ObjectNumber,0.281176)) 
        sketch.setDatum(hpit.ConstraintNumber,App.Units.Quantity(definition.OutputInnerDiameter()))
        hpit.ConstraintNumber += 1
        sketch.addConstraint(Sketcher.Constraint('DistanceX',hpit.ObjectNumber,3,0,3,0.647308)) 
        sketch.setDatum(hpit.ConstraintNumber,App.Units.Quantity(hole.OutputZ()))
        hpit.ConstraintNumber += 1
        sketch.addConstraint(Sketcher.Constraint('DistanceY',0,3,hpit.ObjectNumber,3,0.643353)) 
        sketch.setDatum(hpit.ConstraintNumber,App.Units.Quantity(hole.OutputX()))

    def createHoleTop(hpit,hole):
        sketch.addGeometry(Part.Circle(App.Vector(-0.006343,1.042262,0),App.Vector(0,0,1),0.179877),False)
        hpit.ConstraintNumber += 1
        sketch.addConstraint(Sketcher.Constraint('PointOnObject',hpit.ObjectNumber,3,-2)) 
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',0,3,hpit.ObjectNumber,3,1.042262)) 
        sketch.setDatum(hpit.ConstraintNumber,App.Units.Quantity(hole.OutputX()))
        #sketch.renameConstraint(12, u'Top')

    def createHoleRightTop(hpit,hole):
        sketch.addGeometry(Part.Circle(App.Vector(1.017571,0.952324,0),App.Vector(0,0,1),0.245674),False)
        hpit.ConstraintNumber += 1
        sketch.addConstraint(Sketcher.Constraint('Diameter',hpit.ObjectNumber,0.491348)) 
        sketch.setDatum(hpit.ConstraintNumber,App.Units.Quantity(definition.OutputInnerDiameter()))
        hpit.ConstraintNumber += 1
        sketch.addConstraint(Sketcher.Constraint('DistanceX',0,3,hpit.ObjectNumber,3,1.017571)) 
        sketch.setDatum(hpit.ConstraintNumber,App.Units.Quantity(hole.OutputZ()))
        hpit.ConstraintNumber += 1
        sketch.addConstraint(Sketcher.Constraint('DistanceY',0,3,hpit.ObjectNumber,3,0.952324)) 
        sketch.setDatum(hpit.ConstraintNumber,App.Units.Quantity(hole.OutputX()))

    def createHoleRight(hpit,hole):
        sketch.addGeometry(Part.Circle(App.Vector(0.976061,-0.016243,0),App.Vector(0,0,1),0.271319),False)
        hpit.ConstraintNumber += 1
        sketch.addConstraint(Sketcher.Constraint('PointOnObject',hpit.ObjectNumber,3,-1)) 
        hpit.ConstraintNumber += 1
        sketch.addConstraint(Sketcher.Constraint('Diameter',hpit.ObjectNumber,0.542638)) 
        sketch.setDatum(hpit.ConstraintNumber,App.Units.Quantity(definition.OutputInnerDiameter()))
        hpit.ConstraintNumber += 1
        sketch.addConstraint(Sketcher.Constraint('DistanceX',0,3,hpit.ObjectNumber,3,0.976061)) 
        sketch.setDatum(hpit.ConstraintNumber,App.Units.Quantity(hole.OutputZ()))
        #sketch.renameConstraint(18, u'Right')

    def createHoleRightBottom(hpit,hole):
        sketch.addGeometry(Part.Circle(App.Vector(0.982979,-0.957137,0),App.Vector(0,0,1),0.179877),False)
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',hpit.ObjectNumber,3,0,3,0.957137)) 
        sketch.setDatum(hpit.ConstraintNumber,App.Units.Quantity(hole.OutputX()))
        hpit.ConstraintNumber += 1
        sketch.addConstraint(Sketcher.Constraint('DistanceX',0,3,hpit.ObjectNumber,3,0.982979)) 
        sketch.setDatum(hpit.ConstraintNumber,App.Units.Quantity(hole.OutputZ()))

    def createHoleBottom(hpit,hole):
        sketch.addGeometry(Part.Circle(App.Vector(-0.006343,-1.012484,0),App.Vector(0,0,1),0.196899),False)
        hpit.ConstraintNumber += 1
        sketch.addConstraint(Sketcher.Constraint('PointOnObject',hpit.ObjectNumber,3,-2)) 
        hpit.ConstraintNumber += 1
        sketch.addConstraint(Sketcher.Constraint('Diameter',hpit.ObjectNumber,0.393798)) 
        sketch.setDatum(hpit.ConstraintNumber,App.Units.Quantity(definition.OutputInnerDiameter()))
        hpit.ConstraintNumber += 1
        sketch.addConstraint(Sketcher.Constraint('DistanceY',hpit.ObjectNumber,3,0,3,1.012484)) 
        sketch.setDatum(hpit.ConstraintNumber,App.Units.Quantity(hole.OutputX()))

    def createHoleLeftBottom(hpit,hole):
        sketch.addGeometry(Part.Circle(App.Vector(-1.044094,-0.991729,0),App.Vector(0,0,1),0.179877),False)
        hpit.ConstraintNumber += 1
        sketch.addConstraint(Sketcher.Constraint('Diameter',hpit.ObjectNumber,0.359754)) 
        sketch.setDatum(hpit.ConstraintNumber,App.Units.Quantity(definition.OutputInnerDiameter()))
        hpit.ConstraintNumber += 1
        sketch.addConstraint(Sketcher.Constraint('DistanceY',hpit.ObjectNumber,3,0,3,0.991729)) 
        sketch.setDatum(hpit.ConstraintNumber,App.Units.Quantity(hole.OutputX()))
        hpit.ConstraintNumber += 1
        sketch.addConstraint(Sketcher.Constraint('DistanceX',hpit.ObjectNumber,3,0,3,1.044094)) 
        sketch.setDatum(hpit.ConstraintNumber,App.Units.Quantity(hole.OutputZ()))

    for hole in holes:
        if hole.HolePositionType == HoleType.CENTER:
            createCenterHole(hpi)
        elif hole.HolePositionType == HoleType.RIGHTTOP:
            createHoleRightTop(hpi,hole)
        elif hole.HolePositionType == HoleType.RIGHTBOTTOM:
            createHoleRightBottom(hpi,hole)
        elif hole.HolePositionType == HoleType.LEFTBOTTOM:
            createHoleLeftBottom(hpi,hole)
        elif hole.HolePositionType == HoleType.LEFTTOP:
            createHoleLeftTop(hpi,hole)
        elif hole.HolePositionType == HoleType.TOP:
            createHoleTop(hpi,hole)
        elif hole.HolePositionType == HoleType.RIGHT:
            createHoleRight(hpi,hole)
        elif hole.HolePositionType == HoleType.BOTTOM:
            createHoleBottom(hpi,hole)
        elif hole.HolePositionType == HoleType.LEFT:
            createHoleLeft(hpi,hole)
        
        hpi.ObjectNumber += 1

def paintSketch(sketch, definition, position):
    sketch.Support = (document.getObject('XZ_Plane'),[''])
    sketch.MapMode = 'FlatFace'

    sketch.addGeometry(Part.LineSegment(App.Vector(0.000000,-0.000000,0),App.Vector(-0.001979,1.008049,0)),False)
    sketch.addConstraint(Sketcher.Constraint('Coincident',0,1,-1,1)) 
    sketch.addConstraint(Sketcher.Constraint('PointOnObject',0,2,-2)) 

    sketch.addConstraint(Sketcher.Constraint('DistanceY',0,1,0,2,1.008049)) 
    sketch.setDatum(2,App.Units.Quantity(definition.OutputTotalDepth()))

    sketch.addGeometry(Part.LineSegment(App.Vector(0.000000,1.000000,0),App.Vector(-0.223077,1.008049,0)),False)
    sketch.addConstraint(Sketcher.Constraint('Coincident',1,1,0,2)) 
    sketch.movePoint(1,2,App.Vector(-0.220129,1.002153,0),0)

    sketch.addConstraint(Sketcher.Constraint('Horizontal',1))

    sketch.addConstraint(Sketcher.Constraint('DistanceX',1,2,1,1,0.220129)) 

    sketch.setDatum(5,App.Units.Quantity(definition.OutputInnerRadius()))

    sketch.addGeometry(Part.LineSegment(App.Vector(-0.150000,1.000000,0),App.Vector(-0.139617,0.158150,0)),False)
    sketch.addConstraint(Sketcher.Constraint('Coincident',2,1,1,2)) 
    sketch.addConstraint(Sketcher.Constraint('Vertical',2)) 

    sketch.addConstraint(Sketcher.Constraint('DistanceY',2,2,2,1,0.841850)) 
    sketch.setDatum(8,App.Units.Quantity(definition.OutputStraigthDepth()))

    sketch.addGeometry(Part.LineSegment(App.Vector(-0.150000,0.250000,0),App.Vector(-0.142565,-0.001041,0)),True)
    sketch.addConstraint(Sketcher.Constraint('Coincident',3,1,2,2)) 
    sketch.addConstraint(Sketcher.Constraint('PointOnObject',3,2,-1)) 
    sketch.addConstraint(Sketcher.Constraint('Vertical',3)) 

    sketch.addGeometry(Part.LineSegment(App.Vector(-0.150000,0.250000,0),App.Vector(-0.272368,-0.003883,0)),False)
    sketch.addConstraint(Sketcher.Constraint('Coincident',4,1,2,2)) 
    sketch.addConstraint(Sketcher.Constraint('PointOnObject',4,2,-1)) 

    sketch.addConstraint(Sketcher.Constraint('Angle',4,1,3,1,0.455190)) 
    sketch.setDatum(14,App.Units.Quantity(definition.OutputHoleAngle()))

    sketch.addGeometry(Part.LineSegment(App.Vector(-0.266577,-0.000000,0),App.Vector(0.000000,-0.000000,0)),False)
    sketch.addConstraint(Sketcher.Constraint('Coincident',5,1,4,2)) 
    sketch.addConstraint(Sketcher.Constraint('Coincident',5,2,0,1)) 

    sketch.AttachmentOffset.Base.x = position.X
    sketch.AttachmentOffset.Base.z = position.Z

def createGroove(number):
    grooveName = generateGrooveName(number)

    document.getObject('Body').newObject('PartDesign::Groove',grooveName)

    return document.getObject(grooveName)

def paintGroove(sketch,groove):
    groove.Profile = sketch
    groove.ReferenceAxis = (sketch,['V_Axis'])
    groove.Angle = 360.0
    groove.Midplane = 0
    groove.Reversed = 0
    sketch.Visibility = False

def createHole(number, holeDefinition, holePosition):
    sketch = createSketch(number)

    paintSketch(sketch,holeDefinition,holePosition)

    groove = createGroove(number)

    paintGroove(sketch,groove)

holeList = []
basicHoleDefinition = HoleDefinition(1, 0.3, 0.75, 25)
holeList.append(HolePosition(0,0,HoleType.CENTER))
holeList.append(HolePosition(1,0,HoleType.TOP))
holeList.append(HolePosition(0,1,HoleType.TOP))
holeList.append(HolePosition(-1,0,HoleType.BOTTOM))
holeList.append(HolePosition(0,-1,HoleType.BOTTOM))
holeList.append(HolePosition(1,1,HoleType.RIGHTTOP))
holeList.append(HolePosition(-1,-1,HoleType.LEFTBOTTOM))
holeList.append(HolePosition(-1,1,HoleType.RIGHTBOTTOM))
holeList.append(HolePosition(1,-1,HoleType.LEFTTOP))
holeList.append(HolePosition(2,0,HoleType.TOP))
holeList.append(HolePosition(0,2,HoleType.TOP))
holeList.append(HolePosition(-2,0,HoleType.BOTTOM))
holeList.append(HolePosition(0,-2,HoleType.BOTTOM))
holeList.append(HolePosition(2,1,HoleType.RIGHTTOP))
holeList.append(HolePosition(1,2,HoleType.RIGHTTOP))
holeList.append(HolePosition(-2,1,HoleType.RIGHTBOTTOM))
holeList.append(HolePosition(1,-2,HoleType.LEFTTOP))
holeList.append(HolePosition(2,-1,HoleType.LEFTTOP))
holeList.append(HolePosition(-1,2,HoleType.RIGHTBOTTOM))
holeList.append(HolePosition(-2,-1,HoleType.LEFTBOTTOM))
holeList.append(HolePosition(-1,-2,HoleType.LEFTBOTTOM))
holeList.append(HolePosition(2,2,HoleType.RIGHTTOP))
holeList.append(HolePosition(-2,-2,HoleType.LEFTBOTTOM))
holeList.append(HolePosition(-2,2,HoleType.RIGHTBOTTOM))
holeList.append(HolePosition(2,-2,HoleType.LEFTTOP))
holeList.append(HolePosition(3,0,HoleType.TOP))
holeList.append(HolePosition(0,3,HoleType.TOP))
holeList.append(HolePosition(-3,0,HoleType.BOTTOM))
holeList.append(HolePosition(0,-3,HoleType.BOTTOM))
holeList.append(HolePosition(3,1,HoleType.RIGHTTOP))
holeList.append(HolePosition(1,3,HoleType.RIGHTTOP))
holeList.append(HolePosition(-3,1,HoleType.RIGHTBOTTOM))
holeList.append(HolePosition(1,-3,HoleType.LEFTTOP))
holeList.append(HolePosition(3,-1,HoleType.LEFTTOP))
holeList.append(HolePosition(-1,3,HoleType.RIGHTBOTTOM))
holeList.append(HolePosition(-3,-1,HoleType.LEFTBOTTOM))
holeList.append(HolePosition(-1,-3,HoleType.LEFTBOTTOM))
holeList.append(HolePosition(3,2,HoleType.RIGHTTOP))
holeList.append(HolePosition(2,3,HoleType.RIGHTTOP))
holeList.append(HolePosition(-3,2,HoleType.RIGHTBOTTOM))
holeList.append(HolePosition(2,-3,HoleType.LEFTTOP))
holeList.append(HolePosition(3,-2,HoleType.LEFTTOP))
holeList.append(HolePosition(-2,3,HoleType.RIGHTBOTTOM))
holeList.append(HolePosition(-3,-2,HoleType.LEFTBOTTOM))
holeList.append(HolePosition(-2,-3,HoleType.LEFTBOTTOM))
holeList.append(HolePosition(3,3,HoleType.RIGHTTOP))
holeList.append(HolePosition(-3,-3,HoleType.LEFTBOTTOM))
holeList.append(HolePosition(-3,3,HoleType.RIGHTBOTTOM))
holeList.append(HolePosition(3,-3,HoleType.LEFTTOP))
holeList.append(HolePosition(4,0,HoleType.TOP))
holeList.append(HolePosition(0,4,HoleType.TOP))
holeList.append(HolePosition(-4,0,HoleType.BOTTOM))
holeList.append(HolePosition(0,-4,HoleType.BOTTOM))
holeList.append(HolePosition(4,1,HoleType.RIGHTTOP))
holeList.append(HolePosition(1,4,HoleType.RIGHTTOP))
holeList.append(HolePosition(-4,1,HoleType.RIGHTBOTTOM))
holeList.append(HolePosition(1,-4,HoleType.LEFTTOP))
holeList.append(HolePosition(4,-1,HoleType.LEFTTOP))
holeList.append(HolePosition(-1,4,HoleType.RIGHTBOTTOM))
holeList.append(HolePosition(-4,-1,HoleType.LEFTBOTTOM))
holeList.append(HolePosition(-1,-4,HoleType.LEFTBOTTOM))
holeList.append(HolePosition(4,2,HoleType.RIGHTTOP))
holeList.append(HolePosition(2,4,HoleType.RIGHTTOP))
holeList.append(HolePosition(-4,2,HoleType.RIGHTBOTTOM))
holeList.append(HolePosition(2,-4,HoleType.LEFTTOP))
holeList.append(HolePosition(4,-2,HoleType.LEFTTOP))
holeList.append(HolePosition(-2,4,HoleType.RIGHTBOTTOM))
holeList.append(HolePosition(-4,-2,HoleType.LEFTBOTTOM))
holeList.append(HolePosition(-2,-4,HoleType.LEFTBOTTOM))
holeList.append(HolePosition(4,3,HoleType.RIGHTTOP))
holeList.append(HolePosition(3,4,HoleType.RIGHTTOP))
holeList.append(HolePosition(-4,3,HoleType.RIGHTBOTTOM))
holeList.append(HolePosition(3,-4,HoleType.LEFTTOP))
holeList.append(HolePosition(4,-3,HoleType.LEFTTOP))
holeList.append(HolePosition(-3,4,HoleType.RIGHTBOTTOM))
holeList.append(HolePosition(-4,-3,HoleType.LEFTBOTTOM))
holeList.append(HolePosition(-3,-4,HoleType.LEFTBOTTOM))
holeList.append(HolePosition(4,4,HoleType.RIGHTTOP))
holeList.append(HolePosition(-4,-4,HoleType.LEFTBOTTOM))
holeList.append(HolePosition(-4,4,HoleType.RIGHTBOTTOM))
holeList.append(HolePosition(4,-4,HoleType.LEFTTOP))
holeList.append(HolePosition(5,0,HoleType.TOP))
holeList.append(HolePosition(0,5,HoleType.TOP))
holeList.append(HolePosition(-5,0,HoleType.BOTTOM))
holeList.append(HolePosition(0,-5,HoleType.BOTTOM))
holeList.append(HolePosition(5,1,HoleType.RIGHTTOP))
holeList.append(HolePosition(1,5,HoleType.RIGHTTOP))
holeList.append(HolePosition(-5,1,HoleType.RIGHTBOTTOM))
holeList.append(HolePosition(1,-5,HoleType.LEFTTOP))
holeList.append(HolePosition(5,-1,HoleType.LEFTTOP))
holeList.append(HolePosition(-1,5,HoleType.RIGHTBOTTOM))
holeList.append(HolePosition(-5,-1,HoleType.LEFTBOTTOM))
holeList.append(HolePosition(-1,-5,HoleType.LEFTBOTTOM))
holeList.append(HolePosition(5,2,HoleType.RIGHTTOP))
holeList.append(HolePosition(2,5,HoleType.RIGHTTOP))
holeList.append(HolePosition(-5,2,HoleType.RIGHTBOTTOM))
holeList.append(HolePosition(2,-5,HoleType.LEFTTOP))
holeList.append(HolePosition(5,-2,HoleType.LEFTTOP))
holeList.append(HolePosition(-2,5,HoleType.RIGHTBOTTOM))
holeList.append(HolePosition(-5,-2,HoleType.LEFTBOTTOM))
holeList.append(HolePosition(-2,-5,HoleType.LEFTBOTTOM))
holeList.append(HolePosition(5,3,HoleType.RIGHTTOP))
holeList.append(HolePosition(3,5,HoleType.RIGHTTOP))
holeList.append(HolePosition(-5,3,HoleType.RIGHTBOTTOM))
holeList.append(HolePosition(3,-5,HoleType.LEFTTOP))
holeList.append(HolePosition(5,-3,HoleType.LEFTTOP))
holeList.append(HolePosition(-3,5,HoleType.RIGHTBOTTOM))
holeList.append(HolePosition(-5,-3,HoleType.LEFTBOTTOM))
holeList.append(HolePosition(-3,-5,HoleType.LEFTBOTTOM))
holeList.append(HolePosition(5,4,HoleType.RIGHTTOP))
holeList.append(HolePosition(4,5,HoleType.RIGHTTOP))
holeList.append(HolePosition(-5,4,HoleType.RIGHTBOTTOM))
holeList.append(HolePosition(4,-5,HoleType.LEFTTOP))
holeList.append(HolePosition(5,-4,HoleType.LEFTTOP))
holeList.append(HolePosition(-4,5,HoleType.RIGHTBOTTOM))
holeList.append(HolePosition(-5,-4,HoleType.LEFTBOTTOM))
holeList.append(HolePosition(-4,-5,HoleType.LEFTBOTTOM))
holeList.append(HolePosition(5,5,HoleType.RIGHTTOP))
holeList.append(HolePosition(-5,-5,HoleType.LEFTBOTTOM))
holeList.append(HolePosition(-5,5,HoleType.RIGHTBOTTOM))
holeList.append(HolePosition(5,-5,HoleType.LEFTTOP))
holeList.append(HolePosition(6,0,HoleType.TOP))
holeList.append(HolePosition(0,6,HoleType.TOP))
holeList.append(HolePosition(-6,0,HoleType.BOTTOM))
holeList.append(HolePosition(0,-6,HoleType.BOTTOM))
holeList.append(HolePosition(6,1,HoleType.RIGHTTOP))
holeList.append(HolePosition(1,6,HoleType.RIGHTTOP))
holeList.append(HolePosition(-6,1,HoleType.RIGHTBOTTOM))
holeList.append(HolePosition(1,-6,HoleType.LEFTTOP))
holeList.append(HolePosition(6,-1,HoleType.LEFTTOP))
holeList.append(HolePosition(-1,6,HoleType.RIGHTBOTTOM))
holeList.append(HolePosition(-6,-1,HoleType.LEFTBOTTOM))
holeList.append(HolePosition(-1,-6,HoleType.LEFTBOTTOM))
holeList.append(HolePosition(6,2,HoleType.RIGHTTOP))
holeList.append(HolePosition(2,6,HoleType.RIGHTTOP))
holeList.append(HolePosition(-6,2,HoleType.RIGHTBOTTOM))
holeList.append(HolePosition(2,-6,HoleType.LEFTTOP))
holeList.append(HolePosition(6,-2,HoleType.LEFTTOP))
holeList.append(HolePosition(-2,6,HoleType.RIGHTBOTTOM))
holeList.append(HolePosition(-6,-2,HoleType.LEFTBOTTOM))
holeList.append(HolePosition(-2,-6,HoleType.LEFTBOTTOM))
holeList.append(HolePosition(6,3,HoleType.RIGHTTOP))
holeList.append(HolePosition(3,6,HoleType.RIGHTTOP))
holeList.append(HolePosition(-6,3,HoleType.RIGHTBOTTOM))
holeList.append(HolePosition(3,-6,HoleType.LEFTTOP))
holeList.append(HolePosition(6,-3,HoleType.LEFTTOP))
holeList.append(HolePosition(-3,6,HoleType.RIGHTBOTTOM))
holeList.append(HolePosition(-6,-3,HoleType.LEFTBOTTOM))
holeList.append(HolePosition(-3,-6,HoleType.LEFTBOTTOM))
holeList.append(HolePosition(6,4,HoleType.RIGHTTOP))
holeList.append(HolePosition(4,6,HoleType.RIGHTTOP))
holeList.append(HolePosition(-6,4,HoleType.RIGHTBOTTOM))
holeList.append(HolePosition(4,-6,HoleType.LEFTTOP))
holeList.append(HolePosition(6,-4,HoleType.LEFTTOP))
holeList.append(HolePosition(-4,6,HoleType.RIGHTBOTTOM))
holeList.append(HolePosition(-6,-4,HoleType.LEFTBOTTOM))
holeList.append(HolePosition(-4,-6,HoleType.LEFTBOTTOM))
holeList.append(HolePosition(6,5,HoleType.RIGHTTOP))
holeList.append(HolePosition(5,6,HoleType.RIGHTTOP))
holeList.append(HolePosition(-6,5,HoleType.RIGHTBOTTOM))
holeList.append(HolePosition(5,-6,HoleType.LEFTTOP))
holeList.append(HolePosition(6,-5,HoleType.LEFTTOP))
holeList.append(HolePosition(-5,6,HoleType.RIGHTBOTTOM))
holeList.append(HolePosition(-6,-5,HoleType.LEFTBOTTOM))
holeList.append(HolePosition(-5,-6,HoleType.LEFTBOTTOM))
holeList.append(HolePosition(6,6,HoleType.RIGHTTOP))
holeList.append(HolePosition(-6,-6,HoleType.LEFTBOTTOM))
holeList.append(HolePosition(-6,6,HoleType.RIGHTBOTTOM))
holeList.append(HolePosition(6,-6,HoleType.LEFTTOP))
holeList.append(HolePosition(7,0,HoleType.TOP))
holeList.append(HolePosition(0,7,HoleType.TOP))
holeList.append(HolePosition(-7,0,HoleType.BOTTOM))
holeList.append(HolePosition(0,-7,HoleType.BOTTOM))
holeList.append(HolePosition(7,1,HoleType.RIGHTTOP))
holeList.append(HolePosition(1,7,HoleType.RIGHTTOP))
holeList.append(HolePosition(-7,1,HoleType.RIGHTBOTTOM))
holeList.append(HolePosition(1,-7,HoleType.LEFTTOP))
holeList.append(HolePosition(7,-1,HoleType.LEFTTOP))
holeList.append(HolePosition(-1,7,HoleType.RIGHTBOTTOM))
holeList.append(HolePosition(-7,-1,HoleType.LEFTBOTTOM))
holeList.append(HolePosition(-1,-7,HoleType.LEFTBOTTOM))
holeList.append(HolePosition(7,2,HoleType.RIGHTTOP))
holeList.append(HolePosition(2,7,HoleType.RIGHTTOP))
holeList.append(HolePosition(-7,2,HoleType.RIGHTBOTTOM))
holeList.append(HolePosition(2,-7,HoleType.LEFTTOP))
holeList.append(HolePosition(7,-2,HoleType.LEFTTOP))
holeList.append(HolePosition(-2,7,HoleType.RIGHTBOTTOM))
holeList.append(HolePosition(-7,-2,HoleType.LEFTBOTTOM))
holeList.append(HolePosition(-2,-7,HoleType.LEFTBOTTOM))
holeList.append(HolePosition(7,3,HoleType.RIGHTTOP))
holeList.append(HolePosition(3,7,HoleType.RIGHTTOP))
holeList.append(HolePosition(-7,3,HoleType.RIGHTBOTTOM))
holeList.append(HolePosition(3,-7,HoleType.LEFTTOP))
holeList.append(HolePosition(7,-3,HoleType.LEFTTOP))
holeList.append(HolePosition(-3,7,HoleType.RIGHTBOTTOM))
holeList.append(HolePosition(-7,-3,HoleType.LEFTBOTTOM))
holeList.append(HolePosition(-3,-7,HoleType.LEFTBOTTOM))
holeList.append(HolePosition(7,4,HoleType.RIGHTTOP))
holeList.append(HolePosition(4,7,HoleType.RIGHTTOP))
holeList.append(HolePosition(-7,4,HoleType.RIGHTBOTTOM))
holeList.append(HolePosition(4,-7,HoleType.LEFTTOP))
holeList.append(HolePosition(7,-4,HoleType.LEFTTOP))
holeList.append(HolePosition(-4,7,HoleType.RIGHTBOTTOM))
holeList.append(HolePosition(-7,-4,HoleType.LEFTBOTTOM))
holeList.append(HolePosition(-4,-7,HoleType.LEFTBOTTOM))
holeList.append(HolePosition(7,5,HoleType.RIGHTTOP))
holeList.append(HolePosition(5,7,HoleType.RIGHTTOP))
holeList.append(HolePosition(-7,5,HoleType.RIGHTBOTTOM))
holeList.append(HolePosition(5,-7,HoleType.LEFTTOP))
holeList.append(HolePosition(7,-5,HoleType.LEFTTOP))
holeList.append(HolePosition(-5,7,HoleType.RIGHTBOTTOM))
holeList.append(HolePosition(-7,-5,HoleType.LEFTBOTTOM))
holeList.append(HolePosition(-5,-7,HoleType.LEFTBOTTOM))
holeList.append(HolePosition(7,6,HoleType.RIGHTTOP))
holeList.append(HolePosition(6,7,HoleType.RIGHTTOP))
holeList.append(HolePosition(-7,6,HoleType.RIGHTBOTTOM))
holeList.append(HolePosition(6,-7,HoleType.LEFTTOP))
holeList.append(HolePosition(7,-6,HoleType.LEFTTOP))
holeList.append(HolePosition(-6,7,HoleType.RIGHTBOTTOM))
holeList.append(HolePosition(-7,-6,HoleType.LEFTBOTTOM))
holeList.append(HolePosition(-6,-7,HoleType.LEFTBOTTOM))
holeList.append(HolePosition(7,7,HoleType.RIGHTTOP))
holeList.append(HolePosition(-7,-7,HoleType.LEFTBOTTOM))
holeList.append(HolePosition(-7,7,HoleType.RIGHTBOTTOM))
holeList.append(HolePosition(7,-7,HoleType.LEFTTOP))
holeList.append(HolePosition(8,0,HoleType.TOP))
holeList.append(HolePosition(0,8,HoleType.TOP))
holeList.append(HolePosition(-8,0,HoleType.BOTTOM))
holeList.append(HolePosition(0,-8,HoleType.BOTTOM))
holeList.append(HolePosition(8,1,HoleType.RIGHTTOP))
holeList.append(HolePosition(1,8,HoleType.RIGHTTOP))
holeList.append(HolePosition(-8,1,HoleType.RIGHTBOTTOM))
holeList.append(HolePosition(1,-8,HoleType.LEFTTOP))
holeList.append(HolePosition(8,-1,HoleType.LEFTTOP))
holeList.append(HolePosition(-1,8,HoleType.RIGHTBOTTOM))
holeList.append(HolePosition(-8,-1,HoleType.LEFTBOTTOM))
holeList.append(HolePosition(-1,-8,HoleType.LEFTBOTTOM))
holeList.append(HolePosition(8,2,HoleType.RIGHTTOP))
holeList.append(HolePosition(2,8,HoleType.RIGHTTOP))
holeList.append(HolePosition(-8,2,HoleType.RIGHTBOTTOM))
holeList.append(HolePosition(2,-8,HoleType.LEFTTOP))
holeList.append(HolePosition(8,-2,HoleType.LEFTTOP))
holeList.append(HolePosition(-2,8,HoleType.RIGHTBOTTOM))
holeList.append(HolePosition(-8,-2,HoleType.LEFTBOTTOM))
holeList.append(HolePosition(-2,-8,HoleType.LEFTBOTTOM))
holeList.append(HolePosition(8,3,HoleType.RIGHTTOP))
holeList.append(HolePosition(3,8,HoleType.RIGHTTOP))
holeList.append(HolePosition(-8,3,HoleType.RIGHTBOTTOM))
holeList.append(HolePosition(3,-8,HoleType.LEFTTOP))
holeList.append(HolePosition(8,-3,HoleType.LEFTTOP))
holeList.append(HolePosition(-3,8,HoleType.RIGHTBOTTOM))
holeList.append(HolePosition(-8,-3,HoleType.LEFTBOTTOM))
holeList.append(HolePosition(-3,-8,HoleType.LEFTBOTTOM))
holeList.append(HolePosition(8,4,HoleType.RIGHTTOP))
holeList.append(HolePosition(4,8,HoleType.RIGHTTOP))
holeList.append(HolePosition(-8,4,HoleType.RIGHTBOTTOM))
holeList.append(HolePosition(4,-8,HoleType.LEFTTOP))
holeList.append(HolePosition(8,-4,HoleType.LEFTTOP))
holeList.append(HolePosition(-4,8,HoleType.RIGHTBOTTOM))
holeList.append(HolePosition(-8,-4,HoleType.LEFTBOTTOM))
holeList.append(HolePosition(-4,-8,HoleType.LEFTBOTTOM))
holeList.append(HolePosition(8,5,HoleType.RIGHTTOP))
holeList.append(HolePosition(5,8,HoleType.RIGHTTOP))
holeList.append(HolePosition(-8,5,HoleType.RIGHTBOTTOM))
holeList.append(HolePosition(5,-8,HoleType.LEFTTOP))
holeList.append(HolePosition(8,-5,HoleType.LEFTTOP))
holeList.append(HolePosition(-5,8,HoleType.RIGHTBOTTOM))
holeList.append(HolePosition(-8,-5,HoleType.LEFTBOTTOM))
holeList.append(HolePosition(-5,-8,HoleType.LEFTBOTTOM))
holeList.append(HolePosition(8,6,HoleType.RIGHTTOP))
holeList.append(HolePosition(6,8,HoleType.RIGHTTOP))
holeList.append(HolePosition(-8,6,HoleType.RIGHTBOTTOM))
holeList.append(HolePosition(6,-8,HoleType.LEFTTOP))
holeList.append(HolePosition(8,-6,HoleType.LEFTTOP))
holeList.append(HolePosition(-6,8,HoleType.RIGHTBOTTOM))
holeList.append(HolePosition(-8,-6,HoleType.LEFTBOTTOM))
holeList.append(HolePosition(-6,-8,HoleType.LEFTBOTTOM))
holeList.append(HolePosition(8,7,HoleType.RIGHTTOP))
holeList.append(HolePosition(7,8,HoleType.RIGHTTOP))
holeList.append(HolePosition(-8,7,HoleType.RIGHTBOTTOM))
holeList.append(HolePosition(7,-8,HoleType.LEFTTOP))
holeList.append(HolePosition(8,-7,HoleType.LEFTTOP))
holeList.append(HolePosition(-7,8,HoleType.RIGHTBOTTOM))
holeList.append(HolePosition(-8,-7,HoleType.LEFTBOTTOM))
holeList.append(HolePosition(-7,-8,HoleType.LEFTBOTTOM))
holeList.append(HolePosition(8,8,HoleType.RIGHTTOP))
holeList.append(HolePosition(-8,-8,HoleType.LEFTBOTTOM))
holeList.append(HolePosition(-8,8,HoleType.RIGHTBOTTOM))
holeList.append(HolePosition(8,-8,HoleType.LEFTTOP))
holeList.append(HolePosition(9,0,HoleType.TOP))
holeList.append(HolePosition(0,9,HoleType.TOP))
holeList.append(HolePosition(-9,0,HoleType.BOTTOM))
holeList.append(HolePosition(0,-9,HoleType.BOTTOM))
holeList.append(HolePosition(9,1,HoleType.RIGHTTOP))
holeList.append(HolePosition(1,9,HoleType.RIGHTTOP))
holeList.append(HolePosition(-9,1,HoleType.RIGHTBOTTOM))
holeList.append(HolePosition(1,-9,HoleType.LEFTTOP))
holeList.append(HolePosition(9,-1,HoleType.LEFTTOP))
holeList.append(HolePosition(-1,9,HoleType.RIGHTBOTTOM))
holeList.append(HolePosition(-9,-1,HoleType.LEFTBOTTOM))
holeList.append(HolePosition(-1,-9,HoleType.LEFTBOTTOM))
holeList.append(HolePosition(9,2,HoleType.RIGHTTOP))
holeList.append(HolePosition(2,9,HoleType.RIGHTTOP))
holeList.append(HolePosition(-9,2,HoleType.RIGHTBOTTOM))
holeList.append(HolePosition(2,-9,HoleType.LEFTTOP))
holeList.append(HolePosition(9,-2,HoleType.LEFTTOP))
holeList.append(HolePosition(-2,9,HoleType.RIGHTBOTTOM))
holeList.append(HolePosition(-9,-2,HoleType.LEFTBOTTOM))
holeList.append(HolePosition(-2,-9,HoleType.LEFTBOTTOM))
holeList.append(HolePosition(9,3,HoleType.RIGHTTOP))
holeList.append(HolePosition(3,9,HoleType.RIGHTTOP))
holeList.append(HolePosition(-9,3,HoleType.RIGHTBOTTOM))
holeList.append(HolePosition(3,-9,HoleType.LEFTTOP))
holeList.append(HolePosition(9,-3,HoleType.LEFTTOP))
holeList.append(HolePosition(-3,9,HoleType.RIGHTBOTTOM))
holeList.append(HolePosition(-9,-3,HoleType.LEFTBOTTOM))
holeList.append(HolePosition(-3,-9,HoleType.LEFTBOTTOM))
holeList.append(HolePosition(9,4,HoleType.RIGHTTOP))
holeList.append(HolePosition(4,9,HoleType.RIGHTTOP))
holeList.append(HolePosition(-9,4,HoleType.RIGHTBOTTOM))
holeList.append(HolePosition(4,-9,HoleType.LEFTTOP))
holeList.append(HolePosition(9,-4,HoleType.LEFTTOP))
holeList.append(HolePosition(-4,9,HoleType.RIGHTBOTTOM))
holeList.append(HolePosition(-9,-4,HoleType.LEFTBOTTOM))
holeList.append(HolePosition(-4,-9,HoleType.LEFTBOTTOM))
holeList.append(HolePosition(9,5,HoleType.RIGHTTOP))
holeList.append(HolePosition(5,9,HoleType.RIGHTTOP))
holeList.append(HolePosition(-9,5,HoleType.RIGHTBOTTOM))
holeList.append(HolePosition(5,-9,HoleType.LEFTTOP))
holeList.append(HolePosition(9,-5,HoleType.LEFTTOP))
holeList.append(HolePosition(-5,9,HoleType.RIGHTBOTTOM))
holeList.append(HolePosition(-9,-5,HoleType.LEFTBOTTOM))
holeList.append(HolePosition(-5,-9,HoleType.LEFTBOTTOM))
holeList.append(HolePosition(9,6,HoleType.RIGHTTOP))
holeList.append(HolePosition(6,9,HoleType.RIGHTTOP))
holeList.append(HolePosition(-9,6,HoleType.RIGHTBOTTOM))
holeList.append(HolePosition(6,-9,HoleType.LEFTTOP))
holeList.append(HolePosition(9,-6,HoleType.LEFTTOP))
holeList.append(HolePosition(-6,9,HoleType.RIGHTBOTTOM))
holeList.append(HolePosition(-9,-6,HoleType.LEFTBOTTOM))
holeList.append(HolePosition(-6,-9,HoleType.LEFTBOTTOM))
holeList.append(HolePosition(9,7,HoleType.RIGHTTOP))
holeList.append(HolePosition(7,9,HoleType.RIGHTTOP))
holeList.append(HolePosition(-9,7,HoleType.RIGHTBOTTOM))
holeList.append(HolePosition(7,-9,HoleType.LEFTTOP))
holeList.append(HolePosition(9,-7,HoleType.LEFTTOP))
holeList.append(HolePosition(-7,9,HoleType.RIGHTBOTTOM))
holeList.append(HolePosition(-9,-7,HoleType.LEFTBOTTOM))
holeList.append(HolePosition(-7,-9,HoleType.LEFTBOTTOM))
holeList.append(HolePosition(9,8,HoleType.RIGHTTOP))
holeList.append(HolePosition(8,9,HoleType.RIGHTTOP))
holeList.append(HolePosition(-9,8,HoleType.RIGHTBOTTOM))
holeList.append(HolePosition(8,-9,HoleType.LEFTTOP))
holeList.append(HolePosition(9,-8,HoleType.LEFTTOP))
holeList.append(HolePosition(-8,9,HoleType.RIGHTBOTTOM))
holeList.append(HolePosition(-9,-8,HoleType.LEFTBOTTOM))
holeList.append(HolePosition(-8,-9,HoleType.LEFTBOTTOM))
holeList.append(HolePosition(9,9,HoleType.RIGHTTOP))
holeList.append(HolePosition(-9,-9,HoleType.LEFTBOTTOM))
holeList.append(HolePosition(-9,9,HoleType.RIGHTBOTTOM))
holeList.append(HolePosition(9,-9,HoleType.LEFTTOP))
holeList.append(HolePosition(10,0,HoleType.TOP))
holeList.append(HolePosition(0,10,HoleType.TOP))
holeList.append(HolePosition(-10,0,HoleType.BOTTOM))
holeList.append(HolePosition(0,-10,HoleType.BOTTOM))
holeList.append(HolePosition(10,1,HoleType.RIGHTTOP))
holeList.append(HolePosition(1,10,HoleType.RIGHTTOP))
holeList.append(HolePosition(-10,1,HoleType.RIGHTBOTTOM))
holeList.append(HolePosition(1,-10,HoleType.LEFTTOP))
holeList.append(HolePosition(10,-1,HoleType.LEFTTOP))
holeList.append(HolePosition(-1,10,HoleType.RIGHTBOTTOM))
holeList.append(HolePosition(-10,-1,HoleType.LEFTBOTTOM))
holeList.append(HolePosition(-1,-10,HoleType.LEFTBOTTOM))
holeList.append(HolePosition(10,2,HoleType.RIGHTTOP))
holeList.append(HolePosition(2,10,HoleType.RIGHTTOP))
holeList.append(HolePosition(-10,2,HoleType.RIGHTBOTTOM))
holeList.append(HolePosition(2,-10,HoleType.LEFTTOP))
holeList.append(HolePosition(10,-2,HoleType.LEFTTOP))
holeList.append(HolePosition(-2,10,HoleType.RIGHTBOTTOM))
holeList.append(HolePosition(-10,-2,HoleType.LEFTBOTTOM))
holeList.append(HolePosition(-2,-10,HoleType.LEFTBOTTOM))
holeList.append(HolePosition(10,3,HoleType.RIGHTTOP))
holeList.append(HolePosition(3,10,HoleType.RIGHTTOP))
holeList.append(HolePosition(-10,3,HoleType.RIGHTBOTTOM))
holeList.append(HolePosition(3,-10,HoleType.LEFTTOP))
holeList.append(HolePosition(10,-3,HoleType.LEFTTOP))
holeList.append(HolePosition(-3,10,HoleType.RIGHTBOTTOM))
holeList.append(HolePosition(-10,-3,HoleType.LEFTBOTTOM))
holeList.append(HolePosition(-3,-10,HoleType.LEFTBOTTOM))
holeList.append(HolePosition(10,4,HoleType.RIGHTTOP))
holeList.append(HolePosition(4,10,HoleType.RIGHTTOP))
holeList.append(HolePosition(-10,4,HoleType.RIGHTBOTTOM))
holeList.append(HolePosition(4,-10,HoleType.LEFTTOP))
holeList.append(HolePosition(10,-4,HoleType.LEFTTOP))
holeList.append(HolePosition(-4,10,HoleType.RIGHTBOTTOM))
holeList.append(HolePosition(-10,-4,HoleType.LEFTBOTTOM))
holeList.append(HolePosition(-4,-10,HoleType.LEFTBOTTOM))
holeList.append(HolePosition(10,5,HoleType.RIGHTTOP))
holeList.append(HolePosition(5,10,HoleType.RIGHTTOP))
holeList.append(HolePosition(-10,5,HoleType.RIGHTBOTTOM))
holeList.append(HolePosition(5,-10,HoleType.LEFTTOP))
holeList.append(HolePosition(10,-5,HoleType.LEFTTOP))
holeList.append(HolePosition(-5,10,HoleType.RIGHTBOTTOM))
holeList.append(HolePosition(-10,-5,HoleType.LEFTBOTTOM))
holeList.append(HolePosition(-5,-10,HoleType.LEFTBOTTOM))
holeList.append(HolePosition(10,6,HoleType.RIGHTTOP))
holeList.append(HolePosition(6,10,HoleType.RIGHTTOP))
holeList.append(HolePosition(-10,6,HoleType.RIGHTBOTTOM))
holeList.append(HolePosition(6,-10,HoleType.LEFTTOP))
holeList.append(HolePosition(10,-6,HoleType.LEFTTOP))
holeList.append(HolePosition(-6,10,HoleType.RIGHTBOTTOM))
holeList.append(HolePosition(-10,-6,HoleType.LEFTBOTTOM))
holeList.append(HolePosition(-6,-10,HoleType.LEFTBOTTOM))
holeList.append(HolePosition(10,7,HoleType.RIGHTTOP))
holeList.append(HolePosition(7,10,HoleType.RIGHTTOP))
holeList.append(HolePosition(-10,7,HoleType.RIGHTBOTTOM))
holeList.append(HolePosition(7,-10,HoleType.LEFTTOP))
holeList.append(HolePosition(10,-7,HoleType.LEFTTOP))
holeList.append(HolePosition(-7,10,HoleType.RIGHTBOTTOM))
holeList.append(HolePosition(-10,-7,HoleType.LEFTBOTTOM))
holeList.append(HolePosition(-7,-10,HoleType.LEFTBOTTOM))
holeList.append(HolePosition(10,8,HoleType.RIGHTTOP))
holeList.append(HolePosition(8,10,HoleType.RIGHTTOP))
holeList.append(HolePosition(-10,8,HoleType.RIGHTBOTTOM))
holeList.append(HolePosition(8,-10,HoleType.LEFTTOP))
holeList.append(HolePosition(10,-8,HoleType.LEFTTOP))
holeList.append(HolePosition(-8,10,HoleType.RIGHTBOTTOM))
holeList.append(HolePosition(-10,-8,HoleType.LEFTBOTTOM))
holeList.append(HolePosition(-8,-10,HoleType.LEFTBOTTOM))
holeList.append(HolePosition(10,9,HoleType.RIGHTTOP))
holeList.append(HolePosition(9,10,HoleType.RIGHTTOP))
holeList.append(HolePosition(-10,9,HoleType.RIGHTBOTTOM))
holeList.append(HolePosition(9,-10,HoleType.LEFTTOP))
holeList.append(HolePosition(10,-9,HoleType.LEFTTOP))
holeList.append(HolePosition(-9,10,HoleType.RIGHTBOTTOM))
holeList.append(HolePosition(-10,-9,HoleType.LEFTBOTTOM))
holeList.append(HolePosition(-9,-10,HoleType.LEFTBOTTOM))
holeList.append(HolePosition(10,10,HoleType.RIGHTTOP))
holeList.append(HolePosition(-10,-10,HoleType.LEFTBOTTOM))
holeList.append(HolePosition(-10,10,HoleType.RIGHTBOTTOM))
holeList.append(HolePosition(10,-10,HoleType.LEFTTOP))
holeList.append(HolePosition(11,0,HoleType.TOP))
holeList.append(HolePosition(0,11,HoleType.TOP))
holeList.append(HolePosition(-11,0,HoleType.BOTTOM))
holeList.append(HolePosition(0,-11,HoleType.BOTTOM))
holeList.append(HolePosition(11,1,HoleType.RIGHTTOP))
holeList.append(HolePosition(1,11,HoleType.RIGHTTOP))
holeList.append(HolePosition(-11,1,HoleType.RIGHTBOTTOM))
holeList.append(HolePosition(1,-11,HoleType.LEFTTOP))
holeList.append(HolePosition(11,-1,HoleType.LEFTTOP))
holeList.append(HolePosition(-1,11,HoleType.RIGHTBOTTOM))
holeList.append(HolePosition(-11,-1,HoleType.LEFTBOTTOM))
holeList.append(HolePosition(-1,-11,HoleType.LEFTBOTTOM))
holeList.append(HolePosition(11,2,HoleType.RIGHTTOP))
holeList.append(HolePosition(2,11,HoleType.RIGHTTOP))
holeList.append(HolePosition(-11,2,HoleType.RIGHTBOTTOM))
holeList.append(HolePosition(2,-11,HoleType.LEFTTOP))
holeList.append(HolePosition(11,-2,HoleType.LEFTTOP))
holeList.append(HolePosition(-2,11,HoleType.RIGHTBOTTOM))
holeList.append(HolePosition(-11,-2,HoleType.LEFTBOTTOM))
holeList.append(HolePosition(-2,-11,HoleType.LEFTBOTTOM))
holeList.append(HolePosition(11,3,HoleType.RIGHTTOP))
holeList.append(HolePosition(3,11,HoleType.RIGHTTOP))
holeList.append(HolePosition(-11,3,HoleType.RIGHTBOTTOM))
holeList.append(HolePosition(3,-11,HoleType.LEFTTOP))
holeList.append(HolePosition(11,-3,HoleType.LEFTTOP))
holeList.append(HolePosition(-3,11,HoleType.RIGHTBOTTOM))
holeList.append(HolePosition(-11,-3,HoleType.LEFTBOTTOM))
holeList.append(HolePosition(-3,-11,HoleType.LEFTBOTTOM))
holeList.append(HolePosition(11,4,HoleType.RIGHTTOP))
holeList.append(HolePosition(4,11,HoleType.RIGHTTOP))
holeList.append(HolePosition(-11,4,HoleType.RIGHTBOTTOM))
holeList.append(HolePosition(4,-11,HoleType.LEFTTOP))
holeList.append(HolePosition(11,-4,HoleType.LEFTTOP))
holeList.append(HolePosition(-4,11,HoleType.RIGHTBOTTOM))
holeList.append(HolePosition(-11,-4,HoleType.LEFTBOTTOM))
holeList.append(HolePosition(-4,-11,HoleType.LEFTBOTTOM))
holeList.append(HolePosition(11,5,HoleType.RIGHTTOP))
holeList.append(HolePosition(5,11,HoleType.RIGHTTOP))
holeList.append(HolePosition(-11,5,HoleType.RIGHTBOTTOM))
holeList.append(HolePosition(5,-11,HoleType.LEFTTOP))
holeList.append(HolePosition(11,-5,HoleType.LEFTTOP))
holeList.append(HolePosition(-5,11,HoleType.RIGHTBOTTOM))
holeList.append(HolePosition(-11,-5,HoleType.LEFTBOTTOM))
holeList.append(HolePosition(-5,-11,HoleType.LEFTBOTTOM))
holeList.append(HolePosition(11,6,HoleType.RIGHTTOP))
holeList.append(HolePosition(6,11,HoleType.RIGHTTOP))
holeList.append(HolePosition(-11,6,HoleType.RIGHTBOTTOM))
holeList.append(HolePosition(6,-11,HoleType.LEFTTOP))
holeList.append(HolePosition(11,-6,HoleType.LEFTTOP))
holeList.append(HolePosition(-6,11,HoleType.RIGHTBOTTOM))
holeList.append(HolePosition(-11,-6,HoleType.LEFTBOTTOM))
holeList.append(HolePosition(-6,-11,HoleType.LEFTBOTTOM))
holeList.append(HolePosition(11,7,HoleType.RIGHTTOP))
holeList.append(HolePosition(7,11,HoleType.RIGHTTOP))
holeList.append(HolePosition(-11,7,HoleType.RIGHTBOTTOM))
holeList.append(HolePosition(7,-11,HoleType.LEFTTOP))
holeList.append(HolePosition(11,-7,HoleType.LEFTTOP))
holeList.append(HolePosition(-7,11,HoleType.RIGHTBOTTOM))
holeList.append(HolePosition(-11,-7,HoleType.LEFTBOTTOM))
holeList.append(HolePosition(-7,-11,HoleType.LEFTBOTTOM))
holeList.append(HolePosition(11,8,HoleType.RIGHTTOP))
holeList.append(HolePosition(8,11,HoleType.RIGHTTOP))
holeList.append(HolePosition(-11,8,HoleType.RIGHTBOTTOM))
holeList.append(HolePosition(8,-11,HoleType.LEFTTOP))
holeList.append(HolePosition(11,-8,HoleType.LEFTTOP))
holeList.append(HolePosition(-8,11,HoleType.RIGHTBOTTOM))
holeList.append(HolePosition(-11,-8,HoleType.LEFTBOTTOM))
holeList.append(HolePosition(-8,-11,HoleType.LEFTBOTTOM))
holeList.append(HolePosition(11,9,HoleType.RIGHTTOP))
holeList.append(HolePosition(9,11,HoleType.RIGHTTOP))
holeList.append(HolePosition(-11,9,HoleType.RIGHTBOTTOM))
holeList.append(HolePosition(9,-11,HoleType.LEFTTOP))
holeList.append(HolePosition(11,-9,HoleType.LEFTTOP))
holeList.append(HolePosition(-9,11,HoleType.RIGHTBOTTOM))
holeList.append(HolePosition(-11,-9,HoleType.LEFTBOTTOM))
holeList.append(HolePosition(-9,-11,HoleType.LEFTBOTTOM))
holeList.append(HolePosition(11,10,HoleType.RIGHTTOP))
holeList.append(HolePosition(10,11,HoleType.RIGHTTOP))
holeList.append(HolePosition(-11,10,HoleType.RIGHTBOTTOM))
holeList.append(HolePosition(10,-11,HoleType.LEFTTOP))
holeList.append(HolePosition(11,-10,HoleType.LEFTTOP))
holeList.append(HolePosition(-10,11,HoleType.RIGHTBOTTOM))
holeList.append(HolePosition(-11,-10,HoleType.LEFTBOTTOM))
holeList.append(HolePosition(-10,-11,HoleType.LEFTBOTTOM))
holeList.append(HolePosition(11,11,HoleType.RIGHTTOP))
holeList.append(HolePosition(-11,-11,HoleType.LEFTBOTTOM))
holeList.append(HolePosition(-11,11,HoleType.RIGHTBOTTOM))
holeList.append(HolePosition(11,-11,HoleType.LEFTTOP))
holeList.append(HolePosition(12,0,HoleType.TOP))
holeList.append(HolePosition(0,12,HoleType.TOP))
holeList.append(HolePosition(-12,0,HoleType.BOTTOM))
holeList.append(HolePosition(0,-12,HoleType.BOTTOM))
holeList.append(HolePosition(12,1,HoleType.RIGHTTOP))
holeList.append(HolePosition(1,12,HoleType.RIGHTTOP))
holeList.append(HolePosition(-12,1,HoleType.RIGHTBOTTOM))
holeList.append(HolePosition(1,-12,HoleType.LEFTTOP))
holeList.append(HolePosition(12,-1,HoleType.LEFTTOP))
holeList.append(HolePosition(-1,12,HoleType.RIGHTBOTTOM))
holeList.append(HolePosition(-12,-1,HoleType.LEFTBOTTOM))
holeList.append(HolePosition(-1,-12,HoleType.LEFTBOTTOM))
holeList.append(HolePosition(12,2,HoleType.RIGHTTOP))
holeList.append(HolePosition(2,12,HoleType.RIGHTTOP))
holeList.append(HolePosition(-12,2,HoleType.RIGHTBOTTOM))
holeList.append(HolePosition(2,-12,HoleType.LEFTTOP))
holeList.append(HolePosition(12,-2,HoleType.LEFTTOP))
holeList.append(HolePosition(-2,12,HoleType.RIGHTBOTTOM))
holeList.append(HolePosition(-12,-2,HoleType.LEFTBOTTOM))
holeList.append(HolePosition(-2,-12,HoleType.LEFTBOTTOM))
holeList.append(HolePosition(12,3,HoleType.RIGHTTOP))
holeList.append(HolePosition(3,12,HoleType.RIGHTTOP))
holeList.append(HolePosition(-12,3,HoleType.RIGHTBOTTOM))
holeList.append(HolePosition(3,-12,HoleType.LEFTTOP))
holeList.append(HolePosition(12,-3,HoleType.LEFTTOP))
holeList.append(HolePosition(-3,12,HoleType.RIGHTBOTTOM))
holeList.append(HolePosition(-12,-3,HoleType.LEFTBOTTOM))
holeList.append(HolePosition(-3,-12,HoleType.LEFTBOTTOM))
holeList.append(HolePosition(12,4,HoleType.RIGHTTOP))
holeList.append(HolePosition(4,12,HoleType.RIGHTTOP))
holeList.append(HolePosition(-12,4,HoleType.RIGHTBOTTOM))
holeList.append(HolePosition(4,-12,HoleType.LEFTTOP))
holeList.append(HolePosition(12,-4,HoleType.LEFTTOP))
holeList.append(HolePosition(-4,12,HoleType.RIGHTBOTTOM))
holeList.append(HolePosition(-12,-4,HoleType.LEFTBOTTOM))
holeList.append(HolePosition(-4,-12,HoleType.LEFTBOTTOM))
holeList.append(HolePosition(12,5,HoleType.RIGHTTOP))
holeList.append(HolePosition(5,12,HoleType.RIGHTTOP))
holeList.append(HolePosition(-12,5,HoleType.RIGHTBOTTOM))
holeList.append(HolePosition(5,-12,HoleType.LEFTTOP))
holeList.append(HolePosition(12,-5,HoleType.LEFTTOP))
holeList.append(HolePosition(-5,12,HoleType.RIGHTBOTTOM))
holeList.append(HolePosition(-12,-5,HoleType.LEFTBOTTOM))
holeList.append(HolePosition(-5,-12,HoleType.LEFTBOTTOM))
holeList.append(HolePosition(12,6,HoleType.RIGHTTOP))
holeList.append(HolePosition(6,12,HoleType.RIGHTTOP))
holeList.append(HolePosition(-12,6,HoleType.RIGHTBOTTOM))
holeList.append(HolePosition(6,-12,HoleType.LEFTTOP))
holeList.append(HolePosition(12,-6,HoleType.LEFTTOP))
holeList.append(HolePosition(-6,12,HoleType.RIGHTBOTTOM))
holeList.append(HolePosition(-12,-6,HoleType.LEFTBOTTOM))
holeList.append(HolePosition(-6,-12,HoleType.LEFTBOTTOM))
holeList.append(HolePosition(12,7,HoleType.RIGHTTOP))
holeList.append(HolePosition(7,12,HoleType.RIGHTTOP))
holeList.append(HolePosition(-12,7,HoleType.RIGHTBOTTOM))
holeList.append(HolePosition(7,-12,HoleType.LEFTTOP))
holeList.append(HolePosition(12,-7,HoleType.LEFTTOP))
holeList.append(HolePosition(-7,12,HoleType.RIGHTBOTTOM))
holeList.append(HolePosition(-12,-7,HoleType.LEFTBOTTOM))
holeList.append(HolePosition(-7,-12,HoleType.LEFTBOTTOM))
holeList.append(HolePosition(12,8,HoleType.RIGHTTOP))
holeList.append(HolePosition(8,12,HoleType.RIGHTTOP))
holeList.append(HolePosition(-12,8,HoleType.RIGHTBOTTOM))
holeList.append(HolePosition(8,-12,HoleType.LEFTTOP))
holeList.append(HolePosition(12,-8,HoleType.LEFTTOP))
holeList.append(HolePosition(-8,12,HoleType.RIGHTBOTTOM))
holeList.append(HolePosition(-12,-8,HoleType.LEFTBOTTOM))
holeList.append(HolePosition(-8,-12,HoleType.LEFTBOTTOM))
holeList.append(HolePosition(12,9,HoleType.RIGHTTOP))
holeList.append(HolePosition(9,12,HoleType.RIGHTTOP))
holeList.append(HolePosition(-12,9,HoleType.RIGHTBOTTOM))
holeList.append(HolePosition(9,-12,HoleType.LEFTTOP))
holeList.append(HolePosition(12,-9,HoleType.LEFTTOP))
holeList.append(HolePosition(-9,12,HoleType.RIGHTBOTTOM))
holeList.append(HolePosition(-12,-9,HoleType.LEFTBOTTOM))
holeList.append(HolePosition(-9,-12,HoleType.LEFTBOTTOM))
holeList.append(HolePosition(12,10,HoleType.RIGHTTOP))
holeList.append(HolePosition(10,12,HoleType.RIGHTTOP))
holeList.append(HolePosition(-12,10,HoleType.RIGHTBOTTOM))
holeList.append(HolePosition(10,-12,HoleType.LEFTTOP))
holeList.append(HolePosition(12,-10,HoleType.LEFTTOP))
holeList.append(HolePosition(-10,12,HoleType.RIGHTBOTTOM))
holeList.append(HolePosition(-12,-10,HoleType.LEFTBOTTOM))
holeList.append(HolePosition(-10,-12,HoleType.LEFTBOTTOM))
holeList.append(HolePosition(12,11,HoleType.RIGHTTOP))
holeList.append(HolePosition(11,12,HoleType.RIGHTTOP))
holeList.append(HolePosition(-12,11,HoleType.RIGHTBOTTOM))
holeList.append(HolePosition(11,-12,HoleType.LEFTTOP))
holeList.append(HolePosition(12,-11,HoleType.LEFTTOP))
holeList.append(HolePosition(-11,12,HoleType.RIGHTBOTTOM))
holeList.append(HolePosition(-12,-11,HoleType.LEFTBOTTOM))
holeList.append(HolePosition(-11,-12,HoleType.LEFTBOTTOM))
holeList.append(HolePosition(12,12,HoleType.RIGHTTOP))
holeList.append(HolePosition(-12,-12,HoleType.LEFTBOTTOM))
holeList.append(HolePosition(-12,12,HoleType.RIGHTBOTTOM))
holeList.append(HolePosition(12,-12,HoleType.LEFTTOP))
holeList.append(HolePosition(13,0,HoleType.TOP))
holeList.append(HolePosition(0,13,HoleType.TOP))
holeList.append(HolePosition(-13,0,HoleType.BOTTOM))
holeList.append(HolePosition(0,-13,HoleType.BOTTOM))
holeList.append(HolePosition(13,1,HoleType.RIGHTTOP))
holeList.append(HolePosition(1,13,HoleType.RIGHTTOP))
holeList.append(HolePosition(-13,1,HoleType.RIGHTBOTTOM))
holeList.append(HolePosition(1,-13,HoleType.LEFTTOP))
holeList.append(HolePosition(13,-1,HoleType.LEFTTOP))
holeList.append(HolePosition(-1,13,HoleType.RIGHTBOTTOM))
holeList.append(HolePosition(-13,-1,HoleType.LEFTBOTTOM))
holeList.append(HolePosition(-1,-13,HoleType.LEFTBOTTOM))
holeList.append(HolePosition(13,2,HoleType.RIGHTTOP))
holeList.append(HolePosition(2,13,HoleType.RIGHTTOP))
holeList.append(HolePosition(-13,2,HoleType.RIGHTBOTTOM))
holeList.append(HolePosition(2,-13,HoleType.LEFTTOP))
holeList.append(HolePosition(13,-2,HoleType.LEFTTOP))
holeList.append(HolePosition(-2,13,HoleType.RIGHTBOTTOM))
holeList.append(HolePosition(-13,-2,HoleType.LEFTBOTTOM))
holeList.append(HolePosition(-2,-13,HoleType.LEFTBOTTOM))
holeList.append(HolePosition(13,3,HoleType.RIGHTTOP))
holeList.append(HolePosition(3,13,HoleType.RIGHTTOP))
holeList.append(HolePosition(-13,3,HoleType.RIGHTBOTTOM))
holeList.append(HolePosition(3,-13,HoleType.LEFTTOP))
holeList.append(HolePosition(13,-3,HoleType.LEFTTOP))
holeList.append(HolePosition(-3,13,HoleType.RIGHTBOTTOM))
holeList.append(HolePosition(-13,-3,HoleType.LEFTBOTTOM))
holeList.append(HolePosition(-3,-13,HoleType.LEFTBOTTOM))
holeList.append(HolePosition(13,4,HoleType.RIGHTTOP))
holeList.append(HolePosition(4,13,HoleType.RIGHTTOP))
holeList.append(HolePosition(-13,4,HoleType.RIGHTBOTTOM))
holeList.append(HolePosition(4,-13,HoleType.LEFTTOP))
holeList.append(HolePosition(13,-4,HoleType.LEFTTOP))
holeList.append(HolePosition(-4,13,HoleType.RIGHTBOTTOM))
holeList.append(HolePosition(-13,-4,HoleType.LEFTBOTTOM))
holeList.append(HolePosition(-4,-13,HoleType.LEFTBOTTOM))
holeList.append(HolePosition(13,5,HoleType.RIGHTTOP))
holeList.append(HolePosition(5,13,HoleType.RIGHTTOP))
holeList.append(HolePosition(-13,5,HoleType.RIGHTBOTTOM))
holeList.append(HolePosition(5,-13,HoleType.LEFTTOP))
holeList.append(HolePosition(13,-5,HoleType.LEFTTOP))
holeList.append(HolePosition(-5,13,HoleType.RIGHTBOTTOM))
holeList.append(HolePosition(-13,-5,HoleType.LEFTBOTTOM))
holeList.append(HolePosition(-5,-13,HoleType.LEFTBOTTOM))
holeList.append(HolePosition(13,6,HoleType.RIGHTTOP))
holeList.append(HolePosition(6,13,HoleType.RIGHTTOP))
holeList.append(HolePosition(-13,6,HoleType.RIGHTBOTTOM))
holeList.append(HolePosition(6,-13,HoleType.LEFTTOP))
holeList.append(HolePosition(13,-6,HoleType.LEFTTOP))
holeList.append(HolePosition(-6,13,HoleType.RIGHTBOTTOM))
holeList.append(HolePosition(-13,-6,HoleType.LEFTBOTTOM))
holeList.append(HolePosition(-6,-13,HoleType.LEFTBOTTOM))
holeList.append(HolePosition(13,7,HoleType.RIGHTTOP))
holeList.append(HolePosition(7,13,HoleType.RIGHTTOP))
holeList.append(HolePosition(-13,7,HoleType.RIGHTBOTTOM))
holeList.append(HolePosition(7,-13,HoleType.LEFTTOP))
holeList.append(HolePosition(13,-7,HoleType.LEFTTOP))
holeList.append(HolePosition(-7,13,HoleType.RIGHTBOTTOM))
holeList.append(HolePosition(-13,-7,HoleType.LEFTBOTTOM))
holeList.append(HolePosition(-7,-13,HoleType.LEFTBOTTOM))
holeList.append(HolePosition(13,8,HoleType.RIGHTTOP))
holeList.append(HolePosition(8,13,HoleType.RIGHTTOP))
holeList.append(HolePosition(-13,8,HoleType.RIGHTBOTTOM))
holeList.append(HolePosition(8,-13,HoleType.LEFTTOP))
holeList.append(HolePosition(13,-8,HoleType.LEFTTOP))
holeList.append(HolePosition(-8,13,HoleType.RIGHTBOTTOM))
holeList.append(HolePosition(-13,-8,HoleType.LEFTBOTTOM))
holeList.append(HolePosition(-8,-13,HoleType.LEFTBOTTOM))
holeList.append(HolePosition(13,9,HoleType.RIGHTTOP))
holeList.append(HolePosition(9,13,HoleType.RIGHTTOP))
holeList.append(HolePosition(-13,9,HoleType.RIGHTBOTTOM))
holeList.append(HolePosition(9,-13,HoleType.LEFTTOP))
holeList.append(HolePosition(13,-9,HoleType.LEFTTOP))
holeList.append(HolePosition(-9,13,HoleType.RIGHTBOTTOM))
holeList.append(HolePosition(-13,-9,HoleType.LEFTBOTTOM))
holeList.append(HolePosition(-9,-13,HoleType.LEFTBOTTOM))
holeList.append(HolePosition(13,10,HoleType.RIGHTTOP))
holeList.append(HolePosition(10,13,HoleType.RIGHTTOP))
holeList.append(HolePosition(-13,10,HoleType.RIGHTBOTTOM))
holeList.append(HolePosition(10,-13,HoleType.LEFTTOP))
holeList.append(HolePosition(13,-10,HoleType.LEFTTOP))
holeList.append(HolePosition(-10,13,HoleType.RIGHTBOTTOM))
holeList.append(HolePosition(-13,-10,HoleType.LEFTBOTTOM))
holeList.append(HolePosition(-10,-13,HoleType.LEFTBOTTOM))
holeList.append(HolePosition(13,11,HoleType.RIGHTTOP))
holeList.append(HolePosition(11,13,HoleType.RIGHTTOP))
holeList.append(HolePosition(-13,11,HoleType.RIGHTBOTTOM))
holeList.append(HolePosition(11,-13,HoleType.LEFTTOP))
holeList.append(HolePosition(13,-11,HoleType.LEFTTOP))
holeList.append(HolePosition(-11,13,HoleType.RIGHTBOTTOM))
holeList.append(HolePosition(-13,-11,HoleType.LEFTBOTTOM))
holeList.append(HolePosition(-11,-13,HoleType.LEFTBOTTOM))
holeList.append(HolePosition(13,12,HoleType.RIGHTTOP))
holeList.append(HolePosition(12,13,HoleType.RIGHTTOP))
holeList.append(HolePosition(-13,12,HoleType.RIGHTBOTTOM))
holeList.append(HolePosition(12,-13,HoleType.LEFTTOP))
holeList.append(HolePosition(13,-12,HoleType.LEFTTOP))
holeList.append(HolePosition(-12,13,HoleType.RIGHTBOTTOM))
holeList.append(HolePosition(-13,-12,HoleType.LEFTBOTTOM))
holeList.append(HolePosition(-12,-13,HoleType.LEFTBOTTOM))
holeList.append(HolePosition(13,13,HoleType.RIGHTTOP))
holeList.append(HolePosition(-13,-13,HoleType.LEFTBOTTOM))
holeList.append(HolePosition(-13,13,HoleType.RIGHTBOTTOM))
holeList.append(HolePosition(13,-13,HoleType.LEFTTOP))
holeList.append(HolePosition(14,0,HoleType.TOP))
holeList.append(HolePosition(0,14,HoleType.TOP))
holeList.append(HolePosition(-14,0,HoleType.BOTTOM))
holeList.append(HolePosition(0,-14,HoleType.BOTTOM))
holeList.append(HolePosition(14,1,HoleType.RIGHTTOP))
holeList.append(HolePosition(1,14,HoleType.RIGHTTOP))
holeList.append(HolePosition(-14,1,HoleType.RIGHTBOTTOM))
holeList.append(HolePosition(1,-14,HoleType.LEFTTOP))
holeList.append(HolePosition(14,-1,HoleType.LEFTTOP))
holeList.append(HolePosition(-1,14,HoleType.RIGHTBOTTOM))
holeList.append(HolePosition(-14,-1,HoleType.LEFTBOTTOM))
holeList.append(HolePosition(-1,-14,HoleType.LEFTBOTTOM))
holeList.append(HolePosition(14,2,HoleType.RIGHTTOP))
holeList.append(HolePosition(2,14,HoleType.RIGHTTOP))
holeList.append(HolePosition(-14,2,HoleType.RIGHTBOTTOM))
holeList.append(HolePosition(2,-14,HoleType.LEFTTOP))
holeList.append(HolePosition(14,-2,HoleType.LEFTTOP))
holeList.append(HolePosition(-2,14,HoleType.RIGHTBOTTOM))
holeList.append(HolePosition(-14,-2,HoleType.LEFTBOTTOM))
holeList.append(HolePosition(-2,-14,HoleType.LEFTBOTTOM))
holeList.append(HolePosition(14,3,HoleType.RIGHTTOP))
holeList.append(HolePosition(3,14,HoleType.RIGHTTOP))
holeList.append(HolePosition(-14,3,HoleType.RIGHTBOTTOM))
holeList.append(HolePosition(3,-14,HoleType.LEFTTOP))
holeList.append(HolePosition(14,-3,HoleType.LEFTTOP))
holeList.append(HolePosition(-3,14,HoleType.RIGHTBOTTOM))
holeList.append(HolePosition(-14,-3,HoleType.LEFTBOTTOM))
holeList.append(HolePosition(-3,-14,HoleType.LEFTBOTTOM))
holeList.append(HolePosition(14,4,HoleType.RIGHTTOP))
holeList.append(HolePosition(4,14,HoleType.RIGHTTOP))
holeList.append(HolePosition(-14,4,HoleType.RIGHTBOTTOM))
holeList.append(HolePosition(4,-14,HoleType.LEFTTOP))
holeList.append(HolePosition(14,-4,HoleType.LEFTTOP))
holeList.append(HolePosition(-4,14,HoleType.RIGHTBOTTOM))
holeList.append(HolePosition(-14,-4,HoleType.LEFTBOTTOM))
holeList.append(HolePosition(-4,-14,HoleType.LEFTBOTTOM))
holeList.append(HolePosition(14,5,HoleType.RIGHTTOP))
holeList.append(HolePosition(5,14,HoleType.RIGHTTOP))
holeList.append(HolePosition(-14,5,HoleType.RIGHTBOTTOM))
holeList.append(HolePosition(5,-14,HoleType.LEFTTOP))
holeList.append(HolePosition(14,-5,HoleType.LEFTTOP))
holeList.append(HolePosition(-5,14,HoleType.RIGHTBOTTOM))
holeList.append(HolePosition(-14,-5,HoleType.LEFTBOTTOM))
holeList.append(HolePosition(-5,-14,HoleType.LEFTBOTTOM))
holeList.append(HolePosition(14,6,HoleType.RIGHTTOP))
holeList.append(HolePosition(6,14,HoleType.RIGHTTOP))
holeList.append(HolePosition(-14,6,HoleType.RIGHTBOTTOM))
holeList.append(HolePosition(6,-14,HoleType.LEFTTOP))
holeList.append(HolePosition(14,-6,HoleType.LEFTTOP))
holeList.append(HolePosition(-6,14,HoleType.RIGHTBOTTOM))
holeList.append(HolePosition(-14,-6,HoleType.LEFTBOTTOM))
holeList.append(HolePosition(-6,-14,HoleType.LEFTBOTTOM))
holeList.append(HolePosition(14,7,HoleType.RIGHTTOP))
holeList.append(HolePosition(7,14,HoleType.RIGHTTOP))
holeList.append(HolePosition(-14,7,HoleType.RIGHTBOTTOM))
holeList.append(HolePosition(7,-14,HoleType.LEFTTOP))
holeList.append(HolePosition(14,-7,HoleType.LEFTTOP))
holeList.append(HolePosition(-7,14,HoleType.RIGHTBOTTOM))
holeList.append(HolePosition(-14,-7,HoleType.LEFTBOTTOM))
holeList.append(HolePosition(-7,-14,HoleType.LEFTBOTTOM))
holeList.append(HolePosition(14,8,HoleType.RIGHTTOP))
holeList.append(HolePosition(8,14,HoleType.RIGHTTOP))
holeList.append(HolePosition(-14,8,HoleType.RIGHTBOTTOM))
holeList.append(HolePosition(8,-14,HoleType.LEFTTOP))
holeList.append(HolePosition(14,-8,HoleType.LEFTTOP))
holeList.append(HolePosition(-8,14,HoleType.RIGHTBOTTOM))
holeList.append(HolePosition(-14,-8,HoleType.LEFTBOTTOM))
holeList.append(HolePosition(-8,-14,HoleType.LEFTBOTTOM))
holeList.append(HolePosition(14,9,HoleType.RIGHTTOP))
holeList.append(HolePosition(9,14,HoleType.RIGHTTOP))
holeList.append(HolePosition(-14,9,HoleType.RIGHTBOTTOM))
holeList.append(HolePosition(9,-14,HoleType.LEFTTOP))
holeList.append(HolePosition(14,-9,HoleType.LEFTTOP))
holeList.append(HolePosition(-9,14,HoleType.RIGHTBOTTOM))
holeList.append(HolePosition(-14,-9,HoleType.LEFTBOTTOM))
holeList.append(HolePosition(-9,-14,HoleType.LEFTBOTTOM))
holeList.append(HolePosition(14,10,HoleType.RIGHTTOP))
holeList.append(HolePosition(10,14,HoleType.RIGHTTOP))
holeList.append(HolePosition(-14,10,HoleType.RIGHTBOTTOM))
holeList.append(HolePosition(10,-14,HoleType.LEFTTOP))
holeList.append(HolePosition(14,-10,HoleType.LEFTTOP))
holeList.append(HolePosition(-10,14,HoleType.RIGHTBOTTOM))
holeList.append(HolePosition(-14,-10,HoleType.LEFTBOTTOM))
holeList.append(HolePosition(-10,-14,HoleType.LEFTBOTTOM))
holeList.append(HolePosition(14,11,HoleType.RIGHTTOP))
holeList.append(HolePosition(11,14,HoleType.RIGHTTOP))
holeList.append(HolePosition(-14,11,HoleType.RIGHTBOTTOM))
holeList.append(HolePosition(11,-14,HoleType.LEFTTOP))
holeList.append(HolePosition(14,-11,HoleType.LEFTTOP))
holeList.append(HolePosition(-11,14,HoleType.RIGHTBOTTOM))
holeList.append(HolePosition(-14,-11,HoleType.LEFTBOTTOM))
holeList.append(HolePosition(-11,-14,HoleType.LEFTBOTTOM))
holeList.append(HolePosition(14,12,HoleType.RIGHTTOP))
holeList.append(HolePosition(12,14,HoleType.RIGHTTOP))
holeList.append(HolePosition(-14,12,HoleType.RIGHTBOTTOM))
holeList.append(HolePosition(12,-14,HoleType.LEFTTOP))
holeList.append(HolePosition(14,-12,HoleType.LEFTTOP))
holeList.append(HolePosition(-12,14,HoleType.RIGHTBOTTOM))
holeList.append(HolePosition(-14,-12,HoleType.LEFTBOTTOM))
holeList.append(HolePosition(-12,-14,HoleType.LEFTBOTTOM))
holeList.append(HolePosition(14,13,HoleType.RIGHTTOP))
holeList.append(HolePosition(13,14,HoleType.RIGHTTOP))
holeList.append(HolePosition(-14,13,HoleType.RIGHTBOTTOM))
holeList.append(HolePosition(13,-14,HoleType.LEFTTOP))
holeList.append(HolePosition(14,-13,HoleType.LEFTTOP))
holeList.append(HolePosition(-13,14,HoleType.RIGHTBOTTOM))
holeList.append(HolePosition(-14,-13,HoleType.LEFTBOTTOM))
holeList.append(HolePosition(-13,-14,HoleType.LEFTBOTTOM))
holeList.append(HolePosition(14,14,HoleType.RIGHTTOP))
holeList.append(HolePosition(-14,-14,HoleType.LEFTBOTTOM))
holeList.append(HolePosition(-14,14,HoleType.RIGHTBOTTOM))
holeList.append(HolePosition(14,-14,HoleType.LEFTTOP))
holeList.append(HolePosition(15,0,HoleType.TOP))
holeList.append(HolePosition(0,15,HoleType.TOP))
holeList.append(HolePosition(-15,0,HoleType.BOTTOM))
holeList.append(HolePosition(0,-15,HoleType.BOTTOM))
holeList.append(HolePosition(15,1,HoleType.RIGHTTOP))
holeList.append(HolePosition(1,15,HoleType.RIGHTTOP))
holeList.append(HolePosition(-15,1,HoleType.RIGHTBOTTOM))
holeList.append(HolePosition(1,-15,HoleType.LEFTTOP))
holeList.append(HolePosition(15,-1,HoleType.LEFTTOP))
holeList.append(HolePosition(-1,15,HoleType.RIGHTBOTTOM))
holeList.append(HolePosition(-15,-1,HoleType.LEFTBOTTOM))
holeList.append(HolePosition(-1,-15,HoleType.LEFTBOTTOM))
holeList.append(HolePosition(15,2,HoleType.RIGHTTOP))
holeList.append(HolePosition(2,15,HoleType.RIGHTTOP))
holeList.append(HolePosition(-15,2,HoleType.RIGHTBOTTOM))
holeList.append(HolePosition(2,-15,HoleType.LEFTTOP))
holeList.append(HolePosition(15,-2,HoleType.LEFTTOP))
holeList.append(HolePosition(-2,15,HoleType.RIGHTBOTTOM))
holeList.append(HolePosition(-15,-2,HoleType.LEFTBOTTOM))
holeList.append(HolePosition(-2,-15,HoleType.LEFTBOTTOM))
holeList.append(HolePosition(15,3,HoleType.RIGHTTOP))
holeList.append(HolePosition(3,15,HoleType.RIGHTTOP))
holeList.append(HolePosition(-15,3,HoleType.RIGHTBOTTOM))
holeList.append(HolePosition(3,-15,HoleType.LEFTTOP))
holeList.append(HolePosition(15,-3,HoleType.LEFTTOP))
holeList.append(HolePosition(-3,15,HoleType.RIGHTBOTTOM))
holeList.append(HolePosition(-15,-3,HoleType.LEFTBOTTOM))
holeList.append(HolePosition(-3,-15,HoleType.LEFTBOTTOM))
holeList.append(HolePosition(15,4,HoleType.RIGHTTOP))
holeList.append(HolePosition(4,15,HoleType.RIGHTTOP))
holeList.append(HolePosition(-15,4,HoleType.RIGHTBOTTOM))
holeList.append(HolePosition(4,-15,HoleType.LEFTTOP))
holeList.append(HolePosition(15,-4,HoleType.LEFTTOP))
holeList.append(HolePosition(-4,15,HoleType.RIGHTBOTTOM))
holeList.append(HolePosition(-15,-4,HoleType.LEFTBOTTOM))
holeList.append(HolePosition(-4,-15,HoleType.LEFTBOTTOM))
holeList.append(HolePosition(15,5,HoleType.RIGHTTOP))
holeList.append(HolePosition(5,15,HoleType.RIGHTTOP))
holeList.append(HolePosition(-15,5,HoleType.RIGHTBOTTOM))
holeList.append(HolePosition(5,-15,HoleType.LEFTTOP))
holeList.append(HolePosition(15,-5,HoleType.LEFTTOP))
holeList.append(HolePosition(-5,15,HoleType.RIGHTBOTTOM))
holeList.append(HolePosition(-15,-5,HoleType.LEFTBOTTOM))
holeList.append(HolePosition(-5,-15,HoleType.LEFTBOTTOM))
holeList.append(HolePosition(15,6,HoleType.RIGHTTOP))
holeList.append(HolePosition(6,15,HoleType.RIGHTTOP))
holeList.append(HolePosition(-15,6,HoleType.RIGHTBOTTOM))
holeList.append(HolePosition(6,-15,HoleType.LEFTTOP))
holeList.append(HolePosition(15,-6,HoleType.LEFTTOP))
holeList.append(HolePosition(-6,15,HoleType.RIGHTBOTTOM))
holeList.append(HolePosition(-15,-6,HoleType.LEFTBOTTOM))
holeList.append(HolePosition(-6,-15,HoleType.LEFTBOTTOM))
holeList.append(HolePosition(15,7,HoleType.RIGHTTOP))
holeList.append(HolePosition(7,15,HoleType.RIGHTTOP))
holeList.append(HolePosition(-15,7,HoleType.RIGHTBOTTOM))
holeList.append(HolePosition(7,-15,HoleType.LEFTTOP))
holeList.append(HolePosition(15,-7,HoleType.LEFTTOP))
holeList.append(HolePosition(-7,15,HoleType.RIGHTBOTTOM))
holeList.append(HolePosition(-15,-7,HoleType.LEFTBOTTOM))
holeList.append(HolePosition(-7,-15,HoleType.LEFTBOTTOM))
holeList.append(HolePosition(15,8,HoleType.RIGHTTOP))
holeList.append(HolePosition(8,15,HoleType.RIGHTTOP))
holeList.append(HolePosition(-15,8,HoleType.RIGHTBOTTOM))
holeList.append(HolePosition(8,-15,HoleType.LEFTTOP))
holeList.append(HolePosition(15,-8,HoleType.LEFTTOP))
holeList.append(HolePosition(-8,15,HoleType.RIGHTBOTTOM))
holeList.append(HolePosition(-15,-8,HoleType.LEFTBOTTOM))
holeList.append(HolePosition(-8,-15,HoleType.LEFTBOTTOM))
holeList.append(HolePosition(15,9,HoleType.RIGHTTOP))
holeList.append(HolePosition(9,15,HoleType.RIGHTTOP))
holeList.append(HolePosition(-15,9,HoleType.RIGHTBOTTOM))
holeList.append(HolePosition(9,-15,HoleType.LEFTTOP))
holeList.append(HolePosition(15,-9,HoleType.LEFTTOP))
holeList.append(HolePosition(-9,15,HoleType.RIGHTBOTTOM))
holeList.append(HolePosition(-15,-9,HoleType.LEFTBOTTOM))
holeList.append(HolePosition(-9,-15,HoleType.LEFTBOTTOM))
holeList.append(HolePosition(15,10,HoleType.RIGHTTOP))
holeList.append(HolePosition(10,15,HoleType.RIGHTTOP))
holeList.append(HolePosition(-15,10,HoleType.RIGHTBOTTOM))
holeList.append(HolePosition(10,-15,HoleType.LEFTTOP))
holeList.append(HolePosition(15,-10,HoleType.LEFTTOP))
holeList.append(HolePosition(-10,15,HoleType.RIGHTBOTTOM))
holeList.append(HolePosition(-15,-10,HoleType.LEFTBOTTOM))
holeList.append(HolePosition(-10,-15,HoleType.LEFTBOTTOM))
holeList.append(HolePosition(15,11,HoleType.RIGHTTOP))
holeList.append(HolePosition(11,15,HoleType.RIGHTTOP))
holeList.append(HolePosition(-15,11,HoleType.RIGHTBOTTOM))
holeList.append(HolePosition(11,-15,HoleType.LEFTTOP))
holeList.append(HolePosition(15,-11,HoleType.LEFTTOP))
holeList.append(HolePosition(-11,15,HoleType.RIGHTBOTTOM))
holeList.append(HolePosition(-15,-11,HoleType.LEFTBOTTOM))
holeList.append(HolePosition(-11,-15,HoleType.LEFTBOTTOM))
holeList.append(HolePosition(15,12,HoleType.RIGHTTOP))
holeList.append(HolePosition(12,15,HoleType.RIGHTTOP))
holeList.append(HolePosition(-15,12,HoleType.RIGHTBOTTOM))
holeList.append(HolePosition(12,-15,HoleType.LEFTTOP))
holeList.append(HolePosition(15,-12,HoleType.LEFTTOP))
holeList.append(HolePosition(-12,15,HoleType.RIGHTBOTTOM))
holeList.append(HolePosition(-15,-12,HoleType.LEFTBOTTOM))
holeList.append(HolePosition(-12,-15,HoleType.LEFTBOTTOM))
holeList.append(HolePosition(15,13,HoleType.RIGHTTOP))
holeList.append(HolePosition(13,15,HoleType.RIGHTTOP))
holeList.append(HolePosition(-15,13,HoleType.RIGHTBOTTOM))
holeList.append(HolePosition(13,-15,HoleType.LEFTTOP))
holeList.append(HolePosition(15,-13,HoleType.LEFTTOP))
holeList.append(HolePosition(-13,15,HoleType.RIGHTBOTTOM))
holeList.append(HolePosition(-15,-13,HoleType.LEFTBOTTOM))
holeList.append(HolePosition(-13,-15,HoleType.LEFTBOTTOM))
holeList.append(HolePosition(15,14,HoleType.RIGHTTOP))
holeList.append(HolePosition(14,15,HoleType.RIGHTTOP))
holeList.append(HolePosition(-15,14,HoleType.RIGHTBOTTOM))
holeList.append(HolePosition(14,-15,HoleType.LEFTTOP))
holeList.append(HolePosition(15,-14,HoleType.LEFTTOP))
holeList.append(HolePosition(-14,15,HoleType.RIGHTBOTTOM))
holeList.append(HolePosition(-15,-14,HoleType.LEFTBOTTOM))
holeList.append(HolePosition(-14,-15,HoleType.LEFTBOTTOM))
holeList.append(HolePosition(15,15,HoleType.RIGHTTOP))
holeList.append(HolePosition(-15,-15,HoleType.LEFTBOTTOM))
holeList.append(HolePosition(-15,15,HoleType.RIGHTBOTTOM))
holeList.append(HolePosition(15,-15,HoleType.LEFTTOP))
holeList.append(HolePosition(16,0,HoleType.TOP))
holeList.append(HolePosition(0,16,HoleType.TOP))
holeList.append(HolePosition(-16,0,HoleType.BOTTOM))
holeList.append(HolePosition(0,-16,HoleType.BOTTOM))
holeList.append(HolePosition(16,1,HoleType.RIGHTTOP))
holeList.append(HolePosition(1,16,HoleType.RIGHTTOP))
holeList.append(HolePosition(-16,1,HoleType.RIGHTBOTTOM))
holeList.append(HolePosition(1,-16,HoleType.LEFTTOP))
holeList.append(HolePosition(16,-1,HoleType.LEFTTOP))
holeList.append(HolePosition(-1,16,HoleType.RIGHTBOTTOM))
holeList.append(HolePosition(-16,-1,HoleType.LEFTBOTTOM))
holeList.append(HolePosition(-1,-16,HoleType.LEFTBOTTOM))
holeList.append(HolePosition(16,2,HoleType.RIGHTTOP))
holeList.append(HolePosition(2,16,HoleType.RIGHTTOP))
holeList.append(HolePosition(-16,2,HoleType.RIGHTBOTTOM))
holeList.append(HolePosition(2,-16,HoleType.LEFTTOP))
holeList.append(HolePosition(16,-2,HoleType.LEFTTOP))
holeList.append(HolePosition(-2,16,HoleType.RIGHTBOTTOM))
holeList.append(HolePosition(-16,-2,HoleType.LEFTBOTTOM))
holeList.append(HolePosition(-2,-16,HoleType.LEFTBOTTOM))
holeList.append(HolePosition(16,3,HoleType.RIGHTTOP))
holeList.append(HolePosition(3,16,HoleType.RIGHTTOP))
holeList.append(HolePosition(-16,3,HoleType.RIGHTBOTTOM))
holeList.append(HolePosition(3,-16,HoleType.LEFTTOP))
holeList.append(HolePosition(16,-3,HoleType.LEFTTOP))
holeList.append(HolePosition(-3,16,HoleType.RIGHTBOTTOM))
holeList.append(HolePosition(-16,-3,HoleType.LEFTBOTTOM))
holeList.append(HolePosition(-3,-16,HoleType.LEFTBOTTOM))
holeList.append(HolePosition(16,4,HoleType.RIGHTTOP))
holeList.append(HolePosition(4,16,HoleType.RIGHTTOP))
holeList.append(HolePosition(-16,4,HoleType.RIGHTBOTTOM))
holeList.append(HolePosition(4,-16,HoleType.LEFTTOP))
holeList.append(HolePosition(16,-4,HoleType.LEFTTOP))
holeList.append(HolePosition(-4,16,HoleType.RIGHTBOTTOM))
holeList.append(HolePosition(-16,-4,HoleType.LEFTBOTTOM))
holeList.append(HolePosition(-4,-16,HoleType.LEFTBOTTOM))
holeList.append(HolePosition(16,5,HoleType.RIGHTTOP))
holeList.append(HolePosition(5,16,HoleType.RIGHTTOP))
holeList.append(HolePosition(-16,5,HoleType.RIGHTBOTTOM))
holeList.append(HolePosition(5,-16,HoleType.LEFTTOP))
holeList.append(HolePosition(16,-5,HoleType.LEFTTOP))
holeList.append(HolePosition(-5,16,HoleType.RIGHTBOTTOM))
holeList.append(HolePosition(-16,-5,HoleType.LEFTBOTTOM))
holeList.append(HolePosition(-5,-16,HoleType.LEFTBOTTOM))
holeList.append(HolePosition(16,6,HoleType.RIGHTTOP))
holeList.append(HolePosition(6,16,HoleType.RIGHTTOP))
holeList.append(HolePosition(-16,6,HoleType.RIGHTBOTTOM))
holeList.append(HolePosition(6,-16,HoleType.LEFTTOP))
holeList.append(HolePosition(16,-6,HoleType.LEFTTOP))
holeList.append(HolePosition(-6,16,HoleType.RIGHTBOTTOM))
holeList.append(HolePosition(-16,-6,HoleType.LEFTBOTTOM))
holeList.append(HolePosition(-6,-16,HoleType.LEFTBOTTOM))
holeList.append(HolePosition(16,7,HoleType.RIGHTTOP))
holeList.append(HolePosition(7,16,HoleType.RIGHTTOP))
holeList.append(HolePosition(-16,7,HoleType.RIGHTBOTTOM))
holeList.append(HolePosition(7,-16,HoleType.LEFTTOP))
holeList.append(HolePosition(16,-7,HoleType.LEFTTOP))
holeList.append(HolePosition(-7,16,HoleType.RIGHTBOTTOM))
holeList.append(HolePosition(-16,-7,HoleType.LEFTBOTTOM))
holeList.append(HolePosition(-7,-16,HoleType.LEFTBOTTOM))
holeList.append(HolePosition(16,8,HoleType.RIGHTTOP))
holeList.append(HolePosition(8,16,HoleType.RIGHTTOP))
holeList.append(HolePosition(-16,8,HoleType.RIGHTBOTTOM))
holeList.append(HolePosition(8,-16,HoleType.LEFTTOP))
holeList.append(HolePosition(16,-8,HoleType.LEFTTOP))
holeList.append(HolePosition(-8,16,HoleType.RIGHTBOTTOM))
holeList.append(HolePosition(-16,-8,HoleType.LEFTBOTTOM))
holeList.append(HolePosition(-8,-16,HoleType.LEFTBOTTOM))
holeList.append(HolePosition(16,9,HoleType.RIGHTTOP))
holeList.append(HolePosition(9,16,HoleType.RIGHTTOP))
holeList.append(HolePosition(-16,9,HoleType.RIGHTBOTTOM))
holeList.append(HolePosition(9,-16,HoleType.LEFTTOP))
holeList.append(HolePosition(16,-9,HoleType.LEFTTOP))
holeList.append(HolePosition(-9,16,HoleType.RIGHTBOTTOM))
holeList.append(HolePosition(-16,-9,HoleType.LEFTBOTTOM))
holeList.append(HolePosition(-9,-16,HoleType.LEFTBOTTOM))
holeList.append(HolePosition(16,10,HoleType.RIGHTTOP))
holeList.append(HolePosition(10,16,HoleType.RIGHTTOP))
holeList.append(HolePosition(-16,10,HoleType.RIGHTBOTTOM))
holeList.append(HolePosition(10,-16,HoleType.LEFTTOP))
holeList.append(HolePosition(16,-10,HoleType.LEFTTOP))
holeList.append(HolePosition(-10,16,HoleType.RIGHTBOTTOM))
holeList.append(HolePosition(-16,-10,HoleType.LEFTBOTTOM))
holeList.append(HolePosition(-10,-16,HoleType.LEFTBOTTOM))
holeList.append(HolePosition(16,11,HoleType.RIGHTTOP))
holeList.append(HolePosition(11,16,HoleType.RIGHTTOP))
holeList.append(HolePosition(-16,11,HoleType.RIGHTBOTTOM))
holeList.append(HolePosition(11,-16,HoleType.LEFTTOP))
holeList.append(HolePosition(16,-11,HoleType.LEFTTOP))
holeList.append(HolePosition(-11,16,HoleType.RIGHTBOTTOM))
holeList.append(HolePosition(-16,-11,HoleType.LEFTBOTTOM))
holeList.append(HolePosition(-11,-16,HoleType.LEFTBOTTOM))
holeList.append(HolePosition(16,12,HoleType.RIGHTTOP))
holeList.append(HolePosition(12,16,HoleType.RIGHTTOP))
holeList.append(HolePosition(-16,12,HoleType.RIGHTBOTTOM))
holeList.append(HolePosition(12,-16,HoleType.LEFTTOP))
holeList.append(HolePosition(16,-12,HoleType.LEFTTOP))
holeList.append(HolePosition(-12,16,HoleType.RIGHTBOTTOM))
holeList.append(HolePosition(-16,-12,HoleType.LEFTBOTTOM))
holeList.append(HolePosition(-12,-16,HoleType.LEFTBOTTOM))
holeList.append(HolePosition(16,13,HoleType.RIGHTTOP))
holeList.append(HolePosition(13,16,HoleType.RIGHTTOP))
holeList.append(HolePosition(-16,13,HoleType.RIGHTBOTTOM))
holeList.append(HolePosition(13,-16,HoleType.LEFTTOP))
holeList.append(HolePosition(16,-13,HoleType.LEFTTOP))
holeList.append(HolePosition(-13,16,HoleType.RIGHTBOTTOM))
holeList.append(HolePosition(-16,-13,HoleType.LEFTBOTTOM))
holeList.append(HolePosition(-13,-16,HoleType.LEFTBOTTOM))
holeList.append(HolePosition(16,14,HoleType.RIGHTTOP))
holeList.append(HolePosition(14,16,HoleType.RIGHTTOP))
holeList.append(HolePosition(-16,14,HoleType.RIGHTBOTTOM))
holeList.append(HolePosition(14,-16,HoleType.LEFTTOP))
holeList.append(HolePosition(16,-14,HoleType.LEFTTOP))
holeList.append(HolePosition(-14,16,HoleType.RIGHTBOTTOM))
holeList.append(HolePosition(-16,-14,HoleType.LEFTBOTTOM))
holeList.append(HolePosition(-14,-16,HoleType.LEFTBOTTOM))
holeList.append(HolePosition(16,15,HoleType.RIGHTTOP))
holeList.append(HolePosition(15,16,HoleType.RIGHTTOP))
holeList.append(HolePosition(-16,15,HoleType.RIGHTBOTTOM))
holeList.append(HolePosition(15,-16,HoleType.LEFTTOP))
holeList.append(HolePosition(16,-15,HoleType.LEFTTOP))
holeList.append(HolePosition(-15,16,HoleType.RIGHTBOTTOM))
holeList.append(HolePosition(-16,-15,HoleType.LEFTBOTTOM))
holeList.append(HolePosition(-15,-16,HoleType.LEFTBOTTOM))
holeList.append(HolePosition(16,16,HoleType.RIGHTTOP))
holeList.append(HolePosition(-16,-16,HoleType.LEFTBOTTOM))
holeList.append(HolePosition(-16,16,HoleType.RIGHTBOTTOM))
holeList.append(HolePosition(16,-16,HoleType.LEFTTOP))
holeList.append(HolePosition(17,0,HoleType.TOP))
holeList.append(HolePosition(0,17,HoleType.TOP))
holeList.append(HolePosition(-17,0,HoleType.BOTTOM))
holeList.append(HolePosition(0,-17,HoleType.BOTTOM))
holeList.append(HolePosition(17,1,HoleType.RIGHTTOP))
holeList.append(HolePosition(1,17,HoleType.RIGHTTOP))
holeList.append(HolePosition(-17,1,HoleType.RIGHTBOTTOM))
holeList.append(HolePosition(1,-17,HoleType.LEFTTOP))
holeList.append(HolePosition(17,-1,HoleType.LEFTTOP))
holeList.append(HolePosition(-1,17,HoleType.RIGHTBOTTOM))
holeList.append(HolePosition(-17,-1,HoleType.LEFTBOTTOM))
holeList.append(HolePosition(-1,-17,HoleType.LEFTBOTTOM))
holeList.append(HolePosition(17,2,HoleType.RIGHTTOP))
holeList.append(HolePosition(2,17,HoleType.RIGHTTOP))
holeList.append(HolePosition(-17,2,HoleType.RIGHTBOTTOM))
holeList.append(HolePosition(2,-17,HoleType.LEFTTOP))
holeList.append(HolePosition(17,-2,HoleType.LEFTTOP))
holeList.append(HolePosition(-2,17,HoleType.RIGHTBOTTOM))
holeList.append(HolePosition(-17,-2,HoleType.LEFTBOTTOM))
holeList.append(HolePosition(-2,-17,HoleType.LEFTBOTTOM))
holeList.append(HolePosition(17,3,HoleType.RIGHTTOP))
holeList.append(HolePosition(3,17,HoleType.RIGHTTOP))
holeList.append(HolePosition(-17,3,HoleType.RIGHTBOTTOM))
holeList.append(HolePosition(3,-17,HoleType.LEFTTOP))
holeList.append(HolePosition(17,-3,HoleType.LEFTTOP))
holeList.append(HolePosition(-3,17,HoleType.RIGHTBOTTOM))
holeList.append(HolePosition(-17,-3,HoleType.LEFTBOTTOM))
holeList.append(HolePosition(-3,-17,HoleType.LEFTBOTTOM))
holeList.append(HolePosition(17,4,HoleType.RIGHTTOP))
holeList.append(HolePosition(4,17,HoleType.RIGHTTOP))
holeList.append(HolePosition(-17,4,HoleType.RIGHTBOTTOM))
holeList.append(HolePosition(4,-17,HoleType.LEFTTOP))
holeList.append(HolePosition(17,-4,HoleType.LEFTTOP))
holeList.append(HolePosition(-4,17,HoleType.RIGHTBOTTOM))
holeList.append(HolePosition(-17,-4,HoleType.LEFTBOTTOM))
holeList.append(HolePosition(-4,-17,HoleType.LEFTBOTTOM))
holeList.append(HolePosition(17,5,HoleType.RIGHTTOP))
holeList.append(HolePosition(5,17,HoleType.RIGHTTOP))
holeList.append(HolePosition(-17,5,HoleType.RIGHTBOTTOM))
holeList.append(HolePosition(5,-17,HoleType.LEFTTOP))
holeList.append(HolePosition(17,-5,HoleType.LEFTTOP))
holeList.append(HolePosition(-5,17,HoleType.RIGHTBOTTOM))
holeList.append(HolePosition(-17,-5,HoleType.LEFTBOTTOM))
holeList.append(HolePosition(-5,-17,HoleType.LEFTBOTTOM))
holeList.append(HolePosition(17,6,HoleType.RIGHTTOP))
holeList.append(HolePosition(6,17,HoleType.RIGHTTOP))
holeList.append(HolePosition(-17,6,HoleType.RIGHTBOTTOM))
holeList.append(HolePosition(6,-17,HoleType.LEFTTOP))
holeList.append(HolePosition(17,-6,HoleType.LEFTTOP))
holeList.append(HolePosition(-6,17,HoleType.RIGHTBOTTOM))
holeList.append(HolePosition(-17,-6,HoleType.LEFTBOTTOM))
holeList.append(HolePosition(-6,-17,HoleType.LEFTBOTTOM))
holeList.append(HolePosition(17,7,HoleType.RIGHTTOP))
holeList.append(HolePosition(7,17,HoleType.RIGHTTOP))
holeList.append(HolePosition(-17,7,HoleType.RIGHTBOTTOM))
holeList.append(HolePosition(7,-17,HoleType.LEFTTOP))
holeList.append(HolePosition(17,-7,HoleType.LEFTTOP))
holeList.append(HolePosition(-7,17,HoleType.RIGHTBOTTOM))
holeList.append(HolePosition(-17,-7,HoleType.LEFTBOTTOM))
holeList.append(HolePosition(-7,-17,HoleType.LEFTBOTTOM))
holeList.append(HolePosition(17,8,HoleType.RIGHTTOP))
holeList.append(HolePosition(8,17,HoleType.RIGHTTOP))
holeList.append(HolePosition(-17,8,HoleType.RIGHTBOTTOM))
holeList.append(HolePosition(8,-17,HoleType.LEFTTOP))
holeList.append(HolePosition(17,-8,HoleType.LEFTTOP))
holeList.append(HolePosition(-8,17,HoleType.RIGHTBOTTOM))
holeList.append(HolePosition(-17,-8,HoleType.LEFTBOTTOM))
holeList.append(HolePosition(-8,-17,HoleType.LEFTBOTTOM))
holeList.append(HolePosition(17,9,HoleType.RIGHTTOP))
holeList.append(HolePosition(9,17,HoleType.RIGHTTOP))
holeList.append(HolePosition(-17,9,HoleType.RIGHTBOTTOM))
holeList.append(HolePosition(9,-17,HoleType.LEFTTOP))
holeList.append(HolePosition(17,-9,HoleType.LEFTTOP))
holeList.append(HolePosition(-9,17,HoleType.RIGHTBOTTOM))
holeList.append(HolePosition(-17,-9,HoleType.LEFTBOTTOM))
holeList.append(HolePosition(-9,-17,HoleType.LEFTBOTTOM))
holeList.append(HolePosition(17,10,HoleType.RIGHTTOP))
holeList.append(HolePosition(10,17,HoleType.RIGHTTOP))
holeList.append(HolePosition(-17,10,HoleType.RIGHTBOTTOM))
holeList.append(HolePosition(10,-17,HoleType.LEFTTOP))
holeList.append(HolePosition(17,-10,HoleType.LEFTTOP))
holeList.append(HolePosition(-10,17,HoleType.RIGHTBOTTOM))
holeList.append(HolePosition(-17,-10,HoleType.LEFTBOTTOM))
holeList.append(HolePosition(-10,-17,HoleType.LEFTBOTTOM))
holeList.append(HolePosition(17,11,HoleType.RIGHTTOP))
holeList.append(HolePosition(11,17,HoleType.RIGHTTOP))
holeList.append(HolePosition(-17,11,HoleType.RIGHTBOTTOM))
holeList.append(HolePosition(11,-17,HoleType.LEFTTOP))
holeList.append(HolePosition(17,-11,HoleType.LEFTTOP))
holeList.append(HolePosition(-11,17,HoleType.RIGHTBOTTOM))
holeList.append(HolePosition(-17,-11,HoleType.LEFTBOTTOM))
holeList.append(HolePosition(-11,-17,HoleType.LEFTBOTTOM))
holeList.append(HolePosition(17,12,HoleType.RIGHTTOP))
holeList.append(HolePosition(12,17,HoleType.RIGHTTOP))
holeList.append(HolePosition(-17,12,HoleType.RIGHTBOTTOM))
holeList.append(HolePosition(12,-17,HoleType.LEFTTOP))
holeList.append(HolePosition(17,-12,HoleType.LEFTTOP))
holeList.append(HolePosition(-12,17,HoleType.RIGHTBOTTOM))
holeList.append(HolePosition(-17,-12,HoleType.LEFTBOTTOM))
holeList.append(HolePosition(-12,-17,HoleType.LEFTBOTTOM))
holeList.append(HolePosition(17,13,HoleType.RIGHTTOP))
holeList.append(HolePosition(13,17,HoleType.RIGHTTOP))
holeList.append(HolePosition(-17,13,HoleType.RIGHTBOTTOM))
holeList.append(HolePosition(13,-17,HoleType.LEFTTOP))
holeList.append(HolePosition(17,-13,HoleType.LEFTTOP))
holeList.append(HolePosition(-13,17,HoleType.RIGHTBOTTOM))
holeList.append(HolePosition(-17,-13,HoleType.LEFTBOTTOM))
holeList.append(HolePosition(-13,-17,HoleType.LEFTBOTTOM))
holeList.append(HolePosition(17,14,HoleType.RIGHTTOP))
holeList.append(HolePosition(14,17,HoleType.RIGHTTOP))
holeList.append(HolePosition(-17,14,HoleType.RIGHTBOTTOM))
holeList.append(HolePosition(14,-17,HoleType.LEFTTOP))
holeList.append(HolePosition(17,-14,HoleType.LEFTTOP))
holeList.append(HolePosition(-14,17,HoleType.RIGHTBOTTOM))
holeList.append(HolePosition(-17,-14,HoleType.LEFTBOTTOM))
holeList.append(HolePosition(-14,-17,HoleType.LEFTBOTTOM))
holeList.append(HolePosition(17,15,HoleType.RIGHTTOP))
holeList.append(HolePosition(15,17,HoleType.RIGHTTOP))
holeList.append(HolePosition(-17,15,HoleType.RIGHTBOTTOM))
holeList.append(HolePosition(15,-17,HoleType.LEFTTOP))
holeList.append(HolePosition(17,-15,HoleType.LEFTTOP))
holeList.append(HolePosition(-15,17,HoleType.RIGHTBOTTOM))
holeList.append(HolePosition(-17,-15,HoleType.LEFTBOTTOM))
holeList.append(HolePosition(-15,-17,HoleType.LEFTBOTTOM))
holeList.append(HolePosition(17,16,HoleType.RIGHTTOP))
holeList.append(HolePosition(16,17,HoleType.RIGHTTOP))
holeList.append(HolePosition(-17,16,HoleType.RIGHTBOTTOM))
holeList.append(HolePosition(16,-17,HoleType.LEFTTOP))
holeList.append(HolePosition(17,-16,HoleType.LEFTTOP))
holeList.append(HolePosition(-16,17,HoleType.RIGHTBOTTOM))
holeList.append(HolePosition(-17,-16,HoleType.LEFTBOTTOM))
holeList.append(HolePosition(-16,-17,HoleType.LEFTBOTTOM))
holeList.append(HolePosition(17,17,HoleType.RIGHTTOP))
holeList.append(HolePosition(-17,-17,HoleType.LEFTBOTTOM))
holeList.append(HolePosition(-17,17,HoleType.RIGHTBOTTOM))
holeList.append(HolePosition(17,-17,HoleType.LEFTTOP))
holeList.append(HolePosition(18,0,HoleType.TOP))
holeList.append(HolePosition(0,18,HoleType.TOP))
holeList.append(HolePosition(-18,0,HoleType.BOTTOM))
holeList.append(HolePosition(0,-18,HoleType.BOTTOM))
holeList.append(HolePosition(18,1,HoleType.RIGHTTOP))
holeList.append(HolePosition(1,18,HoleType.RIGHTTOP))
holeList.append(HolePosition(-18,1,HoleType.RIGHTBOTTOM))
holeList.append(HolePosition(1,-18,HoleType.LEFTTOP))
holeList.append(HolePosition(18,-1,HoleType.LEFTTOP))
holeList.append(HolePosition(-1,18,HoleType.RIGHTBOTTOM))
holeList.append(HolePosition(-18,-1,HoleType.LEFTBOTTOM))
holeList.append(HolePosition(-1,-18,HoleType.LEFTBOTTOM))
holeList.append(HolePosition(18,2,HoleType.RIGHTTOP))
holeList.append(HolePosition(2,18,HoleType.RIGHTTOP))
holeList.append(HolePosition(-18,2,HoleType.RIGHTBOTTOM))
holeList.append(HolePosition(2,-18,HoleType.LEFTTOP))
holeList.append(HolePosition(18,-2,HoleType.LEFTTOP))
holeList.append(HolePosition(-2,18,HoleType.RIGHTBOTTOM))
holeList.append(HolePosition(-18,-2,HoleType.LEFTBOTTOM))
holeList.append(HolePosition(-2,-18,HoleType.LEFTBOTTOM))
holeList.append(HolePosition(18,3,HoleType.RIGHTTOP))
holeList.append(HolePosition(3,18,HoleType.RIGHTTOP))
holeList.append(HolePosition(-18,3,HoleType.RIGHTBOTTOM))
holeList.append(HolePosition(3,-18,HoleType.LEFTTOP))
holeList.append(HolePosition(18,-3,HoleType.LEFTTOP))
holeList.append(HolePosition(-3,18,HoleType.RIGHTBOTTOM))
holeList.append(HolePosition(-18,-3,HoleType.LEFTBOTTOM))
holeList.append(HolePosition(-3,-18,HoleType.LEFTBOTTOM))
holeList.append(HolePosition(18,4,HoleType.RIGHTTOP))
holeList.append(HolePosition(4,18,HoleType.RIGHTTOP))
holeList.append(HolePosition(-18,4,HoleType.RIGHTBOTTOM))
holeList.append(HolePosition(4,-18,HoleType.LEFTTOP))
holeList.append(HolePosition(18,-4,HoleType.LEFTTOP))
holeList.append(HolePosition(-4,18,HoleType.RIGHTBOTTOM))
holeList.append(HolePosition(-18,-4,HoleType.LEFTBOTTOM))
holeList.append(HolePosition(-4,-18,HoleType.LEFTBOTTOM))
holeList.append(HolePosition(18,5,HoleType.RIGHTTOP))
holeList.append(HolePosition(5,18,HoleType.RIGHTTOP))
holeList.append(HolePosition(-18,5,HoleType.RIGHTBOTTOM))
holeList.append(HolePosition(5,-18,HoleType.LEFTTOP))
holeList.append(HolePosition(18,-5,HoleType.LEFTTOP))
holeList.append(HolePosition(-5,18,HoleType.RIGHTBOTTOM))
holeList.append(HolePosition(-18,-5,HoleType.LEFTBOTTOM))
holeList.append(HolePosition(-5,-18,HoleType.LEFTBOTTOM))
holeList.append(HolePosition(18,6,HoleType.RIGHTTOP))
holeList.append(HolePosition(6,18,HoleType.RIGHTTOP))
holeList.append(HolePosition(-18,6,HoleType.RIGHTBOTTOM))
holeList.append(HolePosition(6,-18,HoleType.LEFTTOP))
holeList.append(HolePosition(18,-6,HoleType.LEFTTOP))
holeList.append(HolePosition(-6,18,HoleType.RIGHTBOTTOM))
holeList.append(HolePosition(-18,-6,HoleType.LEFTBOTTOM))
holeList.append(HolePosition(-6,-18,HoleType.LEFTBOTTOM))
holeList.append(HolePosition(18,7,HoleType.RIGHTTOP))
holeList.append(HolePosition(7,18,HoleType.RIGHTTOP))
holeList.append(HolePosition(-18,7,HoleType.RIGHTBOTTOM))
holeList.append(HolePosition(7,-18,HoleType.LEFTTOP))
holeList.append(HolePosition(18,-7,HoleType.LEFTTOP))
holeList.append(HolePosition(-7,18,HoleType.RIGHTBOTTOM))
holeList.append(HolePosition(-18,-7,HoleType.LEFTBOTTOM))
holeList.append(HolePosition(-7,-18,HoleType.LEFTBOTTOM))
holeList.append(HolePosition(18,8,HoleType.RIGHTTOP))
holeList.append(HolePosition(8,18,HoleType.RIGHTTOP))
holeList.append(HolePosition(-18,8,HoleType.RIGHTBOTTOM))
holeList.append(HolePosition(8,-18,HoleType.LEFTTOP))
holeList.append(HolePosition(18,-8,HoleType.LEFTTOP))
holeList.append(HolePosition(-8,18,HoleType.RIGHTBOTTOM))
holeList.append(HolePosition(-18,-8,HoleType.LEFTBOTTOM))
holeList.append(HolePosition(-8,-18,HoleType.LEFTBOTTOM))
holeList.append(HolePosition(18,9,HoleType.RIGHTTOP))
holeList.append(HolePosition(9,18,HoleType.RIGHTTOP))
holeList.append(HolePosition(-18,9,HoleType.RIGHTBOTTOM))
holeList.append(HolePosition(9,-18,HoleType.LEFTTOP))
holeList.append(HolePosition(18,-9,HoleType.LEFTTOP))
holeList.append(HolePosition(-9,18,HoleType.RIGHTBOTTOM))
holeList.append(HolePosition(-18,-9,HoleType.LEFTBOTTOM))
holeList.append(HolePosition(-9,-18,HoleType.LEFTBOTTOM))
holeList.append(HolePosition(18,10,HoleType.RIGHTTOP))
holeList.append(HolePosition(10,18,HoleType.RIGHTTOP))
holeList.append(HolePosition(-18,10,HoleType.RIGHTBOTTOM))
holeList.append(HolePosition(10,-18,HoleType.LEFTTOP))
holeList.append(HolePosition(18,-10,HoleType.LEFTTOP))
holeList.append(HolePosition(-10,18,HoleType.RIGHTBOTTOM))
holeList.append(HolePosition(-18,-10,HoleType.LEFTBOTTOM))
holeList.append(HolePosition(-10,-18,HoleType.LEFTBOTTOM))
holeList.append(HolePosition(18,11,HoleType.RIGHTTOP))
holeList.append(HolePosition(11,18,HoleType.RIGHTTOP))
holeList.append(HolePosition(-18,11,HoleType.RIGHTBOTTOM))
holeList.append(HolePosition(11,-18,HoleType.LEFTTOP))
holeList.append(HolePosition(18,-11,HoleType.LEFTTOP))
holeList.append(HolePosition(-11,18,HoleType.RIGHTBOTTOM))
holeList.append(HolePosition(-18,-11,HoleType.LEFTBOTTOM))
holeList.append(HolePosition(-11,-18,HoleType.LEFTBOTTOM))
holeList.append(HolePosition(18,12,HoleType.RIGHTTOP))
holeList.append(HolePosition(12,18,HoleType.RIGHTTOP))
holeList.append(HolePosition(-18,12,HoleType.RIGHTBOTTOM))
holeList.append(HolePosition(12,-18,HoleType.LEFTTOP))
holeList.append(HolePosition(18,-12,HoleType.LEFTTOP))
holeList.append(HolePosition(-12,18,HoleType.RIGHTBOTTOM))
holeList.append(HolePosition(-18,-12,HoleType.LEFTBOTTOM))
holeList.append(HolePosition(-12,-18,HoleType.LEFTBOTTOM))
holeList.append(HolePosition(18,13,HoleType.RIGHTTOP))
holeList.append(HolePosition(13,18,HoleType.RIGHTTOP))
holeList.append(HolePosition(-18,13,HoleType.RIGHTBOTTOM))
holeList.append(HolePosition(13,-18,HoleType.LEFTTOP))
holeList.append(HolePosition(18,-13,HoleType.LEFTTOP))
holeList.append(HolePosition(-13,18,HoleType.RIGHTBOTTOM))
holeList.append(HolePosition(-18,-13,HoleType.LEFTBOTTOM))
holeList.append(HolePosition(-13,-18,HoleType.LEFTBOTTOM))
holeList.append(HolePosition(18,14,HoleType.RIGHTTOP))
holeList.append(HolePosition(14,18,HoleType.RIGHTTOP))
holeList.append(HolePosition(-18,14,HoleType.RIGHTBOTTOM))
holeList.append(HolePosition(14,-18,HoleType.LEFTTOP))
holeList.append(HolePosition(18,-14,HoleType.LEFTTOP))
holeList.append(HolePosition(-14,18,HoleType.RIGHTBOTTOM))
holeList.append(HolePosition(-18,-14,HoleType.LEFTBOTTOM))
holeList.append(HolePosition(-14,-18,HoleType.LEFTBOTTOM))
holeList.append(HolePosition(18,15,HoleType.RIGHTTOP))
holeList.append(HolePosition(15,18,HoleType.RIGHTTOP))
holeList.append(HolePosition(-18,15,HoleType.RIGHTBOTTOM))
holeList.append(HolePosition(15,-18,HoleType.LEFTTOP))
holeList.append(HolePosition(18,-15,HoleType.LEFTTOP))
holeList.append(HolePosition(-15,18,HoleType.RIGHTBOTTOM))
holeList.append(HolePosition(-18,-15,HoleType.LEFTBOTTOM))
holeList.append(HolePosition(-15,-18,HoleType.LEFTBOTTOM))
holeList.append(HolePosition(18,16,HoleType.RIGHTTOP))
holeList.append(HolePosition(16,18,HoleType.RIGHTTOP))
holeList.append(HolePosition(-18,16,HoleType.RIGHTBOTTOM))
holeList.append(HolePosition(16,-18,HoleType.LEFTTOP))
holeList.append(HolePosition(18,-16,HoleType.LEFTTOP))
holeList.append(HolePosition(-16,18,HoleType.RIGHTBOTTOM))
holeList.append(HolePosition(-18,-16,HoleType.LEFTBOTTOM))
holeList.append(HolePosition(-16,-18,HoleType.LEFTBOTTOM))
holeList.append(HolePosition(18,17,HoleType.RIGHTTOP))
holeList.append(HolePosition(17,18,HoleType.RIGHTTOP))
holeList.append(HolePosition(-18,17,HoleType.RIGHTBOTTOM))
holeList.append(HolePosition(17,-18,HoleType.LEFTTOP))
holeList.append(HolePosition(18,-17,HoleType.LEFTTOP))
holeList.append(HolePosition(-17,18,HoleType.RIGHTBOTTOM))
holeList.append(HolePosition(-18,-17,HoleType.LEFTBOTTOM))
holeList.append(HolePosition(-17,-18,HoleType.LEFTBOTTOM))
holeList.append(HolePosition(18,18,HoleType.RIGHTTOP))
holeList.append(HolePosition(-18,-18,HoleType.LEFTBOTTOM))
holeList.append(HolePosition(-18,18,HoleType.RIGHTBOTTOM))
holeList.append(HolePosition(18,-18,HoleType.LEFTTOP))
holeList.append(HolePosition(19,0,HoleType.TOP))
holeList.append(HolePosition(0,19,HoleType.TOP))
holeList.append(HolePosition(-19,0,HoleType.BOTTOM))
holeList.append(HolePosition(0,-19,HoleType.BOTTOM))
holeList.append(HolePosition(19,1,HoleType.RIGHTTOP))
holeList.append(HolePosition(1,19,HoleType.RIGHTTOP))
holeList.append(HolePosition(-19,1,HoleType.RIGHTBOTTOM))
holeList.append(HolePosition(1,-19,HoleType.LEFTTOP))
holeList.append(HolePosition(19,-1,HoleType.LEFTTOP))
holeList.append(HolePosition(-1,19,HoleType.RIGHTBOTTOM))
holeList.append(HolePosition(-19,-1,HoleType.LEFTBOTTOM))
holeList.append(HolePosition(-1,-19,HoleType.LEFTBOTTOM))
holeList.append(HolePosition(19,2,HoleType.RIGHTTOP))
holeList.append(HolePosition(2,19,HoleType.RIGHTTOP))
holeList.append(HolePosition(-19,2,HoleType.RIGHTBOTTOM))
holeList.append(HolePosition(2,-19,HoleType.LEFTTOP))
holeList.append(HolePosition(19,-2,HoleType.LEFTTOP))
holeList.append(HolePosition(-2,19,HoleType.RIGHTBOTTOM))
holeList.append(HolePosition(-19,-2,HoleType.LEFTBOTTOM))
holeList.append(HolePosition(-2,-19,HoleType.LEFTBOTTOM))
holeList.append(HolePosition(19,3,HoleType.RIGHTTOP))
holeList.append(HolePosition(3,19,HoleType.RIGHTTOP))
holeList.append(HolePosition(-19,3,HoleType.RIGHTBOTTOM))
holeList.append(HolePosition(3,-19,HoleType.LEFTTOP))
holeList.append(HolePosition(19,-3,HoleType.LEFTTOP))
holeList.append(HolePosition(-3,19,HoleType.RIGHTBOTTOM))
holeList.append(HolePosition(-19,-3,HoleType.LEFTBOTTOM))
holeList.append(HolePosition(-3,-19,HoleType.LEFTBOTTOM))
holeList.append(HolePosition(19,4,HoleType.RIGHTTOP))
holeList.append(HolePosition(4,19,HoleType.RIGHTTOP))
holeList.append(HolePosition(-19,4,HoleType.RIGHTBOTTOM))
holeList.append(HolePosition(4,-19,HoleType.LEFTTOP))
holeList.append(HolePosition(19,-4,HoleType.LEFTTOP))
holeList.append(HolePosition(-4,19,HoleType.RIGHTBOTTOM))
holeList.append(HolePosition(-19,-4,HoleType.LEFTBOTTOM))
holeList.append(HolePosition(-4,-19,HoleType.LEFTBOTTOM))
holeList.append(HolePosition(19,5,HoleType.RIGHTTOP))
holeList.append(HolePosition(5,19,HoleType.RIGHTTOP))
holeList.append(HolePosition(-19,5,HoleType.RIGHTBOTTOM))
holeList.append(HolePosition(5,-19,HoleType.LEFTTOP))
holeList.append(HolePosition(19,-5,HoleType.LEFTTOP))
holeList.append(HolePosition(-5,19,HoleType.RIGHTBOTTOM))
holeList.append(HolePosition(-19,-5,HoleType.LEFTBOTTOM))
holeList.append(HolePosition(-5,-19,HoleType.LEFTBOTTOM))
holeList.append(HolePosition(19,6,HoleType.RIGHTTOP))
holeList.append(HolePosition(6,19,HoleType.RIGHTTOP))
holeList.append(HolePosition(-19,6,HoleType.RIGHTBOTTOM))
holeList.append(HolePosition(6,-19,HoleType.LEFTTOP))
holeList.append(HolePosition(19,-6,HoleType.LEFTTOP))
holeList.append(HolePosition(-6,19,HoleType.RIGHTBOTTOM))
holeList.append(HolePosition(-19,-6,HoleType.LEFTBOTTOM))
holeList.append(HolePosition(-6,-19,HoleType.LEFTBOTTOM))
holeList.append(HolePosition(19,7,HoleType.RIGHTTOP))
holeList.append(HolePosition(7,19,HoleType.RIGHTTOP))
holeList.append(HolePosition(-19,7,HoleType.RIGHTBOTTOM))
holeList.append(HolePosition(7,-19,HoleType.LEFTTOP))
holeList.append(HolePosition(19,-7,HoleType.LEFTTOP))
holeList.append(HolePosition(-7,19,HoleType.RIGHTBOTTOM))
holeList.append(HolePosition(-19,-7,HoleType.LEFTBOTTOM))
holeList.append(HolePosition(-7,-19,HoleType.LEFTBOTTOM))
holeList.append(HolePosition(19,8,HoleType.RIGHTTOP))
holeList.append(HolePosition(8,19,HoleType.RIGHTTOP))
holeList.append(HolePosition(-19,8,HoleType.RIGHTBOTTOM))
holeList.append(HolePosition(8,-19,HoleType.LEFTTOP))
holeList.append(HolePosition(19,-8,HoleType.LEFTTOP))
holeList.append(HolePosition(-8,19,HoleType.RIGHTBOTTOM))
holeList.append(HolePosition(-19,-8,HoleType.LEFTBOTTOM))
holeList.append(HolePosition(-8,-19,HoleType.LEFTBOTTOM))
holeList.append(HolePosition(19,9,HoleType.RIGHTTOP))
holeList.append(HolePosition(9,19,HoleType.RIGHTTOP))
holeList.append(HolePosition(-19,9,HoleType.RIGHTBOTTOM))
holeList.append(HolePosition(9,-19,HoleType.LEFTTOP))
holeList.append(HolePosition(19,-9,HoleType.LEFTTOP))
holeList.append(HolePosition(-9,19,HoleType.RIGHTBOTTOM))
holeList.append(HolePosition(-19,-9,HoleType.LEFTBOTTOM))
holeList.append(HolePosition(-9,-19,HoleType.LEFTBOTTOM))
holeList.append(HolePosition(19,10,HoleType.RIGHTTOP))
holeList.append(HolePosition(10,19,HoleType.RIGHTTOP))
holeList.append(HolePosition(-19,10,HoleType.RIGHTBOTTOM))
holeList.append(HolePosition(10,-19,HoleType.LEFTTOP))
holeList.append(HolePosition(19,-10,HoleType.LEFTTOP))
holeList.append(HolePosition(-10,19,HoleType.RIGHTBOTTOM))
holeList.append(HolePosition(-19,-10,HoleType.LEFTBOTTOM))
holeList.append(HolePosition(-10,-19,HoleType.LEFTBOTTOM))
holeList.append(HolePosition(19,11,HoleType.RIGHTTOP))
holeList.append(HolePosition(11,19,HoleType.RIGHTTOP))
holeList.append(HolePosition(-19,11,HoleType.RIGHTBOTTOM))
holeList.append(HolePosition(11,-19,HoleType.LEFTTOP))
holeList.append(HolePosition(19,-11,HoleType.LEFTTOP))
holeList.append(HolePosition(-11,19,HoleType.RIGHTBOTTOM))
holeList.append(HolePosition(-19,-11,HoleType.LEFTBOTTOM))
holeList.append(HolePosition(-11,-19,HoleType.LEFTBOTTOM))
holeList.append(HolePosition(19,12,HoleType.RIGHTTOP))
holeList.append(HolePosition(12,19,HoleType.RIGHTTOP))
holeList.append(HolePosition(-19,12,HoleType.RIGHTBOTTOM))
holeList.append(HolePosition(12,-19,HoleType.LEFTTOP))
holeList.append(HolePosition(19,-12,HoleType.LEFTTOP))
holeList.append(HolePosition(-12,19,HoleType.RIGHTBOTTOM))
holeList.append(HolePosition(-19,-12,HoleType.LEFTBOTTOM))
holeList.append(HolePosition(-12,-19,HoleType.LEFTBOTTOM))
holeList.append(HolePosition(19,13,HoleType.RIGHTTOP))
holeList.append(HolePosition(13,19,HoleType.RIGHTTOP))
holeList.append(HolePosition(-19,13,HoleType.RIGHTBOTTOM))
holeList.append(HolePosition(13,-19,HoleType.LEFTTOP))
holeList.append(HolePosition(19,-13,HoleType.LEFTTOP))
holeList.append(HolePosition(-13,19,HoleType.RIGHTBOTTOM))
holeList.append(HolePosition(-19,-13,HoleType.LEFTBOTTOM))
holeList.append(HolePosition(-13,-19,HoleType.LEFTBOTTOM))
holeList.append(HolePosition(19,14,HoleType.RIGHTTOP))
holeList.append(HolePosition(14,19,HoleType.RIGHTTOP))
holeList.append(HolePosition(-19,14,HoleType.RIGHTBOTTOM))
holeList.append(HolePosition(14,-19,HoleType.LEFTTOP))
holeList.append(HolePosition(19,-14,HoleType.LEFTTOP))
holeList.append(HolePosition(-14,19,HoleType.RIGHTBOTTOM))
holeList.append(HolePosition(-19,-14,HoleType.LEFTBOTTOM))
holeList.append(HolePosition(-14,-19,HoleType.LEFTBOTTOM))
holeList.append(HolePosition(19,15,HoleType.RIGHTTOP))
holeList.append(HolePosition(15,19,HoleType.RIGHTTOP))
holeList.append(HolePosition(-19,15,HoleType.RIGHTBOTTOM))
holeList.append(HolePosition(15,-19,HoleType.LEFTTOP))
holeList.append(HolePosition(19,-15,HoleType.LEFTTOP))
holeList.append(HolePosition(-15,19,HoleType.RIGHTBOTTOM))
holeList.append(HolePosition(-19,-15,HoleType.LEFTBOTTOM))
holeList.append(HolePosition(-15,-19,HoleType.LEFTBOTTOM))
holeList.append(HolePosition(19,16,HoleType.RIGHTTOP))
holeList.append(HolePosition(16,19,HoleType.RIGHTTOP))
holeList.append(HolePosition(-19,16,HoleType.RIGHTBOTTOM))
holeList.append(HolePosition(16,-19,HoleType.LEFTTOP))
holeList.append(HolePosition(19,-16,HoleType.LEFTTOP))
holeList.append(HolePosition(-16,19,HoleType.RIGHTBOTTOM))
holeList.append(HolePosition(-19,-16,HoleType.LEFTBOTTOM))
holeList.append(HolePosition(-16,-19,HoleType.LEFTBOTTOM))
holeList.append(HolePosition(19,17,HoleType.RIGHTTOP))
holeList.append(HolePosition(17,19,HoleType.RIGHTTOP))
holeList.append(HolePosition(-19,17,HoleType.RIGHTBOTTOM))
holeList.append(HolePosition(17,-19,HoleType.LEFTTOP))
holeList.append(HolePosition(19,-17,HoleType.LEFTTOP))
holeList.append(HolePosition(-17,19,HoleType.RIGHTBOTTOM))
holeList.append(HolePosition(-19,-17,HoleType.LEFTBOTTOM))
holeList.append(HolePosition(-17,-19,HoleType.LEFTBOTTOM))
holeList.append(HolePosition(19,18,HoleType.RIGHTTOP))
holeList.append(HolePosition(18,19,HoleType.RIGHTTOP))
holeList.append(HolePosition(-19,18,HoleType.RIGHTBOTTOM))
holeList.append(HolePosition(18,-19,HoleType.LEFTTOP))
holeList.append(HolePosition(19,-18,HoleType.LEFTTOP))
holeList.append(HolePosition(-18,19,HoleType.RIGHTBOTTOM))
holeList.append(HolePosition(-19,-18,HoleType.LEFTBOTTOM))
holeList.append(HolePosition(-18,-19,HoleType.LEFTBOTTOM))
holeList.append(HolePosition(19,19,HoleType.RIGHTTOP))
holeList.append(HolePosition(-19,-19,HoleType.LEFTBOTTOM))
holeList.append(HolePosition(-19,19,HoleType.RIGHTBOTTOM))
holeList.append(HolePosition(19,-19,HoleType.LEFTTOP))
holeList.append(HolePosition(20,0,HoleType.TOP))
holeList.append(HolePosition(0,20,HoleType.TOP))
holeList.append(HolePosition(-20,0,HoleType.BOTTOM))
holeList.append(HolePosition(0,-20,HoleType.BOTTOM))
holeList.append(HolePosition(20,1,HoleType.RIGHTTOP))
holeList.append(HolePosition(1,20,HoleType.RIGHTTOP))
holeList.append(HolePosition(-20,1,HoleType.RIGHTBOTTOM))
holeList.append(HolePosition(1,-20,HoleType.LEFTTOP))
holeList.append(HolePosition(20,-1,HoleType.LEFTTOP))
holeList.append(HolePosition(-1,20,HoleType.RIGHTBOTTOM))
holeList.append(HolePosition(-20,-1,HoleType.LEFTBOTTOM))
holeList.append(HolePosition(-1,-20,HoleType.LEFTBOTTOM))
holeList.append(HolePosition(20,2,HoleType.RIGHTTOP))
holeList.append(HolePosition(2,20,HoleType.RIGHTTOP))
holeList.append(HolePosition(-20,2,HoleType.RIGHTBOTTOM))
holeList.append(HolePosition(2,-20,HoleType.LEFTTOP))
holeList.append(HolePosition(20,-2,HoleType.LEFTTOP))
holeList.append(HolePosition(-2,20,HoleType.RIGHTBOTTOM))
holeList.append(HolePosition(-20,-2,HoleType.LEFTBOTTOM))
holeList.append(HolePosition(-2,-20,HoleType.LEFTBOTTOM))
holeList.append(HolePosition(20,3,HoleType.RIGHTTOP))
holeList.append(HolePosition(3,20,HoleType.RIGHTTOP))
holeList.append(HolePosition(-20,3,HoleType.RIGHTBOTTOM))
holeList.append(HolePosition(3,-20,HoleType.LEFTTOP))
holeList.append(HolePosition(20,-3,HoleType.LEFTTOP))
holeList.append(HolePosition(-3,20,HoleType.RIGHTBOTTOM))
holeList.append(HolePosition(-20,-3,HoleType.LEFTBOTTOM))
holeList.append(HolePosition(-3,-20,HoleType.LEFTBOTTOM))
holeList.append(HolePosition(20,4,HoleType.RIGHTTOP))
holeList.append(HolePosition(4,20,HoleType.RIGHTTOP))
holeList.append(HolePosition(-20,4,HoleType.RIGHTBOTTOM))
holeList.append(HolePosition(4,-20,HoleType.LEFTTOP))
holeList.append(HolePosition(20,-4,HoleType.LEFTTOP))
holeList.append(HolePosition(-4,20,HoleType.RIGHTBOTTOM))
holeList.append(HolePosition(-20,-4,HoleType.LEFTBOTTOM))
holeList.append(HolePosition(-4,-20,HoleType.LEFTBOTTOM))
holeList.append(HolePosition(20,5,HoleType.RIGHTTOP))
holeList.append(HolePosition(5,20,HoleType.RIGHTTOP))
holeList.append(HolePosition(-20,5,HoleType.RIGHTBOTTOM))
holeList.append(HolePosition(5,-20,HoleType.LEFTTOP))
holeList.append(HolePosition(20,-5,HoleType.LEFTTOP))
holeList.append(HolePosition(-5,20,HoleType.RIGHTBOTTOM))
holeList.append(HolePosition(-20,-5,HoleType.LEFTBOTTOM))
holeList.append(HolePosition(-5,-20,HoleType.LEFTBOTTOM))
holeList.append(HolePosition(20,6,HoleType.RIGHTTOP))
holeList.append(HolePosition(6,20,HoleType.RIGHTTOP))
holeList.append(HolePosition(-20,6,HoleType.RIGHTBOTTOM))
holeList.append(HolePosition(6,-20,HoleType.LEFTTOP))
holeList.append(HolePosition(20,-6,HoleType.LEFTTOP))
holeList.append(HolePosition(-6,20,HoleType.RIGHTBOTTOM))
holeList.append(HolePosition(-20,-6,HoleType.LEFTBOTTOM))
holeList.append(HolePosition(-6,-20,HoleType.LEFTBOTTOM))
holeList.append(HolePosition(20,7,HoleType.RIGHTTOP))
holeList.append(HolePosition(7,20,HoleType.RIGHTTOP))
holeList.append(HolePosition(-20,7,HoleType.RIGHTBOTTOM))
holeList.append(HolePosition(7,-20,HoleType.LEFTTOP))
holeList.append(HolePosition(20,-7,HoleType.LEFTTOP))
holeList.append(HolePosition(-7,20,HoleType.RIGHTBOTTOM))
holeList.append(HolePosition(-20,-7,HoleType.LEFTBOTTOM))
holeList.append(HolePosition(-7,-20,HoleType.LEFTBOTTOM))
holeList.append(HolePosition(20,8,HoleType.RIGHTTOP))
holeList.append(HolePosition(8,20,HoleType.RIGHTTOP))
holeList.append(HolePosition(-20,8,HoleType.RIGHTBOTTOM))
holeList.append(HolePosition(8,-20,HoleType.LEFTTOP))
holeList.append(HolePosition(20,-8,HoleType.LEFTTOP))
holeList.append(HolePosition(-8,20,HoleType.RIGHTBOTTOM))
holeList.append(HolePosition(-20,-8,HoleType.LEFTBOTTOM))
holeList.append(HolePosition(-8,-20,HoleType.LEFTBOTTOM))
holeList.append(HolePosition(20,9,HoleType.RIGHTTOP))
holeList.append(HolePosition(9,20,HoleType.RIGHTTOP))
holeList.append(HolePosition(-20,9,HoleType.RIGHTBOTTOM))
holeList.append(HolePosition(9,-20,HoleType.LEFTTOP))
holeList.append(HolePosition(20,-9,HoleType.LEFTTOP))
holeList.append(HolePosition(-9,20,HoleType.RIGHTBOTTOM))
holeList.append(HolePosition(-20,-9,HoleType.LEFTBOTTOM))
holeList.append(HolePosition(-9,-20,HoleType.LEFTBOTTOM))
holeList.append(HolePosition(20,10,HoleType.RIGHTTOP))
holeList.append(HolePosition(10,20,HoleType.RIGHTTOP))
holeList.append(HolePosition(-20,10,HoleType.RIGHTBOTTOM))
holeList.append(HolePosition(10,-20,HoleType.LEFTTOP))
holeList.append(HolePosition(20,-10,HoleType.LEFTTOP))
holeList.append(HolePosition(-10,20,HoleType.RIGHTBOTTOM))
holeList.append(HolePosition(-20,-10,HoleType.LEFTBOTTOM))
holeList.append(HolePosition(-10,-20,HoleType.LEFTBOTTOM))
holeList.append(HolePosition(20,11,HoleType.RIGHTTOP))
holeList.append(HolePosition(11,20,HoleType.RIGHTTOP))
holeList.append(HolePosition(-20,11,HoleType.RIGHTBOTTOM))
holeList.append(HolePosition(11,-20,HoleType.LEFTTOP))
holeList.append(HolePosition(20,-11,HoleType.LEFTTOP))
holeList.append(HolePosition(-11,20,HoleType.RIGHTBOTTOM))
holeList.append(HolePosition(-20,-11,HoleType.LEFTBOTTOM))
holeList.append(HolePosition(-11,-20,HoleType.LEFTBOTTOM))
holeList.append(HolePosition(20,12,HoleType.RIGHTTOP))
holeList.append(HolePosition(12,20,HoleType.RIGHTTOP))
holeList.append(HolePosition(-20,12,HoleType.RIGHTBOTTOM))
holeList.append(HolePosition(12,-20,HoleType.LEFTTOP))
holeList.append(HolePosition(20,-12,HoleType.LEFTTOP))
holeList.append(HolePosition(-12,20,HoleType.RIGHTBOTTOM))
holeList.append(HolePosition(-20,-12,HoleType.LEFTBOTTOM))
holeList.append(HolePosition(-12,-20,HoleType.LEFTBOTTOM))
holeList.append(HolePosition(20,13,HoleType.RIGHTTOP))
holeList.append(HolePosition(13,20,HoleType.RIGHTTOP))
holeList.append(HolePosition(-20,13,HoleType.RIGHTBOTTOM))
holeList.append(HolePosition(13,-20,HoleType.LEFTTOP))
holeList.append(HolePosition(20,-13,HoleType.LEFTTOP))
holeList.append(HolePosition(-13,20,HoleType.RIGHTBOTTOM))
holeList.append(HolePosition(-20,-13,HoleType.LEFTBOTTOM))
holeList.append(HolePosition(-13,-20,HoleType.LEFTBOTTOM))
holeList.append(HolePosition(20,14,HoleType.RIGHTTOP))
holeList.append(HolePosition(14,20,HoleType.RIGHTTOP))
holeList.append(HolePosition(-20,14,HoleType.RIGHTBOTTOM))
holeList.append(HolePosition(14,-20,HoleType.LEFTTOP))
holeList.append(HolePosition(20,-14,HoleType.LEFTTOP))
holeList.append(HolePosition(-14,20,HoleType.RIGHTBOTTOM))
holeList.append(HolePosition(-20,-14,HoleType.LEFTBOTTOM))
holeList.append(HolePosition(-14,-20,HoleType.LEFTBOTTOM))
holeList.append(HolePosition(20,15,HoleType.RIGHTTOP))
holeList.append(HolePosition(15,20,HoleType.RIGHTTOP))
holeList.append(HolePosition(-20,15,HoleType.RIGHTBOTTOM))
holeList.append(HolePosition(15,-20,HoleType.LEFTTOP))
holeList.append(HolePosition(20,-15,HoleType.LEFTTOP))
holeList.append(HolePosition(-15,20,HoleType.RIGHTBOTTOM))
holeList.append(HolePosition(-20,-15,HoleType.LEFTBOTTOM))
holeList.append(HolePosition(-15,-20,HoleType.LEFTBOTTOM))
holeList.append(HolePosition(20,16,HoleType.RIGHTTOP))
holeList.append(HolePosition(16,20,HoleType.RIGHTTOP))
holeList.append(HolePosition(-20,16,HoleType.RIGHTBOTTOM))
holeList.append(HolePosition(16,-20,HoleType.LEFTTOP))
holeList.append(HolePosition(20,-16,HoleType.LEFTTOP))
holeList.append(HolePosition(-16,20,HoleType.RIGHTBOTTOM))
holeList.append(HolePosition(-20,-16,HoleType.LEFTBOTTOM))
holeList.append(HolePosition(-16,-20,HoleType.LEFTBOTTOM))
holeList.append(HolePosition(20,17,HoleType.RIGHTTOP))
holeList.append(HolePosition(17,20,HoleType.RIGHTTOP))
holeList.append(HolePosition(-20,17,HoleType.RIGHTBOTTOM))
holeList.append(HolePosition(17,-20,HoleType.LEFTTOP))
holeList.append(HolePosition(20,-17,HoleType.LEFTTOP))
holeList.append(HolePosition(-17,20,HoleType.RIGHTBOTTOM))
holeList.append(HolePosition(-20,-17,HoleType.LEFTBOTTOM))
holeList.append(HolePosition(-17,-20,HoleType.LEFTBOTTOM))
holeList.append(HolePosition(20,18,HoleType.RIGHTTOP))
holeList.append(HolePosition(18,20,HoleType.RIGHTTOP))
holeList.append(HolePosition(-20,18,HoleType.RIGHTBOTTOM))
holeList.append(HolePosition(18,-20,HoleType.LEFTTOP))
holeList.append(HolePosition(20,-18,HoleType.LEFTTOP))
holeList.append(HolePosition(-18,20,HoleType.RIGHTBOTTOM))
holeList.append(HolePosition(-20,-18,HoleType.LEFTBOTTOM))
holeList.append(HolePosition(-18,-20,HoleType.LEFTBOTTOM))
holeList.append(HolePosition(20,19,HoleType.RIGHTTOP))
holeList.append(HolePosition(19,20,HoleType.RIGHTTOP))
holeList.append(HolePosition(-20,19,HoleType.RIGHTBOTTOM))
holeList.append(HolePosition(19,-20,HoleType.LEFTTOP))
holeList.append(HolePosition(20,-19,HoleType.LEFTTOP))
holeList.append(HolePosition(-19,20,HoleType.RIGHTBOTTOM))
holeList.append(HolePosition(-20,-19,HoleType.LEFTBOTTOM))
holeList.append(HolePosition(-19,-20,HoleType.LEFTBOTTOM))
holeList.append(HolePosition(20,20,HoleType.RIGHTTOP))
holeList.append(HolePosition(-20,-20,HoleType.LEFTBOTTOM))
holeList.append(HolePosition(-20,20,HoleType.RIGHTBOTTOM))
holeList.append(HolePosition(20,-20,HoleType.LEFTTOP))
holeList.append(HolePosition(21,0,HoleType.TOP))
holeList.append(HolePosition(0,21,HoleType.TOP))
holeList.append(HolePosition(-21,0,HoleType.BOTTOM))
holeList.append(HolePosition(0,-21,HoleType.BOTTOM))
holeList.append(HolePosition(21,1,HoleType.RIGHTTOP))
holeList.append(HolePosition(1,21,HoleType.RIGHTTOP))
holeList.append(HolePosition(-21,1,HoleType.RIGHTBOTTOM))
holeList.append(HolePosition(1,-21,HoleType.LEFTTOP))
holeList.append(HolePosition(21,-1,HoleType.LEFTTOP))
holeList.append(HolePosition(-1,21,HoleType.RIGHTBOTTOM))
holeList.append(HolePosition(-21,-1,HoleType.LEFTBOTTOM))
holeList.append(HolePosition(-1,-21,HoleType.LEFTBOTTOM))
holeList.append(HolePosition(21,2,HoleType.RIGHTTOP))
holeList.append(HolePosition(2,21,HoleType.RIGHTTOP))
holeList.append(HolePosition(-21,2,HoleType.RIGHTBOTTOM))
holeList.append(HolePosition(2,-21,HoleType.LEFTTOP))
holeList.append(HolePosition(21,-2,HoleType.LEFTTOP))
holeList.append(HolePosition(-2,21,HoleType.RIGHTBOTTOM))
holeList.append(HolePosition(-21,-2,HoleType.LEFTBOTTOM))
holeList.append(HolePosition(-2,-21,HoleType.LEFTBOTTOM))
holeList.append(HolePosition(21,3,HoleType.RIGHTTOP))
holeList.append(HolePosition(3,21,HoleType.RIGHTTOP))
holeList.append(HolePosition(-21,3,HoleType.RIGHTBOTTOM))
holeList.append(HolePosition(3,-21,HoleType.LEFTTOP))
holeList.append(HolePosition(21,-3,HoleType.LEFTTOP))
holeList.append(HolePosition(-3,21,HoleType.RIGHTBOTTOM))
holeList.append(HolePosition(-21,-3,HoleType.LEFTBOTTOM))
holeList.append(HolePosition(-3,-21,HoleType.LEFTBOTTOM))
holeList.append(HolePosition(21,4,HoleType.RIGHTTOP))
holeList.append(HolePosition(4,21,HoleType.RIGHTTOP))
holeList.append(HolePosition(-21,4,HoleType.RIGHTBOTTOM))
holeList.append(HolePosition(4,-21,HoleType.LEFTTOP))
holeList.append(HolePosition(21,-4,HoleType.LEFTTOP))
holeList.append(HolePosition(-4,21,HoleType.RIGHTBOTTOM))
holeList.append(HolePosition(-21,-4,HoleType.LEFTBOTTOM))
holeList.append(HolePosition(-4,-21,HoleType.LEFTBOTTOM))
holeList.append(HolePosition(21,5,HoleType.RIGHTTOP))
holeList.append(HolePosition(5,21,HoleType.RIGHTTOP))
holeList.append(HolePosition(-21,5,HoleType.RIGHTBOTTOM))
holeList.append(HolePosition(5,-21,HoleType.LEFTTOP))
holeList.append(HolePosition(21,-5,HoleType.LEFTTOP))
holeList.append(HolePosition(-5,21,HoleType.RIGHTBOTTOM))
holeList.append(HolePosition(-21,-5,HoleType.LEFTBOTTOM))
holeList.append(HolePosition(-5,-21,HoleType.LEFTBOTTOM))
holeList.append(HolePosition(21,6,HoleType.RIGHTTOP))
holeList.append(HolePosition(6,21,HoleType.RIGHTTOP))
holeList.append(HolePosition(-21,6,HoleType.RIGHTBOTTOM))
holeList.append(HolePosition(6,-21,HoleType.LEFTTOP))
holeList.append(HolePosition(21,-6,HoleType.LEFTTOP))
holeList.append(HolePosition(-6,21,HoleType.RIGHTBOTTOM))
holeList.append(HolePosition(-21,-6,HoleType.LEFTBOTTOM))
holeList.append(HolePosition(-6,-21,HoleType.LEFTBOTTOM))
holeList.append(HolePosition(21,7,HoleType.RIGHTTOP))
holeList.append(HolePosition(7,21,HoleType.RIGHTTOP))
holeList.append(HolePosition(-21,7,HoleType.RIGHTBOTTOM))
holeList.append(HolePosition(7,-21,HoleType.LEFTTOP))
holeList.append(HolePosition(21,-7,HoleType.LEFTTOP))
holeList.append(HolePosition(-7,21,HoleType.RIGHTBOTTOM))
holeList.append(HolePosition(-21,-7,HoleType.LEFTBOTTOM))
holeList.append(HolePosition(-7,-21,HoleType.LEFTBOTTOM))
holeList.append(HolePosition(21,8,HoleType.RIGHTTOP))
holeList.append(HolePosition(8,21,HoleType.RIGHTTOP))
holeList.append(HolePosition(-21,8,HoleType.RIGHTBOTTOM))
holeList.append(HolePosition(8,-21,HoleType.LEFTTOP))
holeList.append(HolePosition(21,-8,HoleType.LEFTTOP))
holeList.append(HolePosition(-8,21,HoleType.RIGHTBOTTOM))
holeList.append(HolePosition(-21,-8,HoleType.LEFTBOTTOM))
holeList.append(HolePosition(-8,-21,HoleType.LEFTBOTTOM))
holeList.append(HolePosition(21,9,HoleType.RIGHTTOP))
holeList.append(HolePosition(9,21,HoleType.RIGHTTOP))
holeList.append(HolePosition(-21,9,HoleType.RIGHTBOTTOM))
holeList.append(HolePosition(9,-21,HoleType.LEFTTOP))
holeList.append(HolePosition(21,-9,HoleType.LEFTTOP))
holeList.append(HolePosition(-9,21,HoleType.RIGHTBOTTOM))
holeList.append(HolePosition(-21,-9,HoleType.LEFTBOTTOM))
holeList.append(HolePosition(-9,-21,HoleType.LEFTBOTTOM))
holeList.append(HolePosition(21,10,HoleType.RIGHTTOP))
holeList.append(HolePosition(10,21,HoleType.RIGHTTOP))
holeList.append(HolePosition(-21,10,HoleType.RIGHTBOTTOM))
holeList.append(HolePosition(10,-21,HoleType.LEFTTOP))
holeList.append(HolePosition(21,-10,HoleType.LEFTTOP))
holeList.append(HolePosition(-10,21,HoleType.RIGHTBOTTOM))
holeList.append(HolePosition(-21,-10,HoleType.LEFTBOTTOM))
holeList.append(HolePosition(-10,-21,HoleType.LEFTBOTTOM))
holeList.append(HolePosition(21,11,HoleType.RIGHTTOP))
holeList.append(HolePosition(11,21,HoleType.RIGHTTOP))
holeList.append(HolePosition(-21,11,HoleType.RIGHTBOTTOM))
holeList.append(HolePosition(11,-21,HoleType.LEFTTOP))
holeList.append(HolePosition(21,-11,HoleType.LEFTTOP))
holeList.append(HolePosition(-11,21,HoleType.RIGHTBOTTOM))
holeList.append(HolePosition(-21,-11,HoleType.LEFTBOTTOM))
holeList.append(HolePosition(-11,-21,HoleType.LEFTBOTTOM))
holeList.append(HolePosition(21,12,HoleType.RIGHTTOP))
holeList.append(HolePosition(12,21,HoleType.RIGHTTOP))
holeList.append(HolePosition(-21,12,HoleType.RIGHTBOTTOM))
holeList.append(HolePosition(12,-21,HoleType.LEFTTOP))
holeList.append(HolePosition(21,-12,HoleType.LEFTTOP))
holeList.append(HolePosition(-12,21,HoleType.RIGHTBOTTOM))
holeList.append(HolePosition(-21,-12,HoleType.LEFTBOTTOM))
holeList.append(HolePosition(-12,-21,HoleType.LEFTBOTTOM))
holeList.append(HolePosition(21,13,HoleType.RIGHTTOP))
holeList.append(HolePosition(13,21,HoleType.RIGHTTOP))
holeList.append(HolePosition(-21,13,HoleType.RIGHTBOTTOM))
holeList.append(HolePosition(13,-21,HoleType.LEFTTOP))
holeList.append(HolePosition(21,-13,HoleType.LEFTTOP))
holeList.append(HolePosition(-13,21,HoleType.RIGHTBOTTOM))
holeList.append(HolePosition(-21,-13,HoleType.LEFTBOTTOM))
holeList.append(HolePosition(-13,-21,HoleType.LEFTBOTTOM))
holeList.append(HolePosition(21,14,HoleType.RIGHTTOP))
holeList.append(HolePosition(14,21,HoleType.RIGHTTOP))
holeList.append(HolePosition(-21,14,HoleType.RIGHTBOTTOM))
holeList.append(HolePosition(14,-21,HoleType.LEFTTOP))
holeList.append(HolePosition(21,-14,HoleType.LEFTTOP))
holeList.append(HolePosition(-14,21,HoleType.RIGHTBOTTOM))
holeList.append(HolePosition(-21,-14,HoleType.LEFTBOTTOM))
holeList.append(HolePosition(-14,-21,HoleType.LEFTBOTTOM))
holeList.append(HolePosition(21,15,HoleType.RIGHTTOP))
holeList.append(HolePosition(15,21,HoleType.RIGHTTOP))
holeList.append(HolePosition(-21,15,HoleType.RIGHTBOTTOM))
holeList.append(HolePosition(15,-21,HoleType.LEFTTOP))
holeList.append(HolePosition(21,-15,HoleType.LEFTTOP))
holeList.append(HolePosition(-15,21,HoleType.RIGHTBOTTOM))
holeList.append(HolePosition(-21,-15,HoleType.LEFTBOTTOM))
holeList.append(HolePosition(-15,-21,HoleType.LEFTBOTTOM))
holeList.append(HolePosition(21,16,HoleType.RIGHTTOP))
holeList.append(HolePosition(16,21,HoleType.RIGHTTOP))
holeList.append(HolePosition(-21,16,HoleType.RIGHTBOTTOM))
holeList.append(HolePosition(16,-21,HoleType.LEFTTOP))
holeList.append(HolePosition(21,-16,HoleType.LEFTTOP))
holeList.append(HolePosition(-16,21,HoleType.RIGHTBOTTOM))
holeList.append(HolePosition(-21,-16,HoleType.LEFTBOTTOM))
holeList.append(HolePosition(-16,-21,HoleType.LEFTBOTTOM))
holeList.append(HolePosition(21,17,HoleType.RIGHTTOP))
holeList.append(HolePosition(17,21,HoleType.RIGHTTOP))
holeList.append(HolePosition(-21,17,HoleType.RIGHTBOTTOM))
holeList.append(HolePosition(17,-21,HoleType.LEFTTOP))
holeList.append(HolePosition(21,-17,HoleType.LEFTTOP))
holeList.append(HolePosition(-17,21,HoleType.RIGHTBOTTOM))
holeList.append(HolePosition(-21,-17,HoleType.LEFTBOTTOM))
holeList.append(HolePosition(-17,-21,HoleType.LEFTBOTTOM))
holeList.append(HolePosition(21,18,HoleType.RIGHTTOP))
holeList.append(HolePosition(18,21,HoleType.RIGHTTOP))
holeList.append(HolePosition(-21,18,HoleType.RIGHTBOTTOM))
holeList.append(HolePosition(18,-21,HoleType.LEFTTOP))
holeList.append(HolePosition(21,-18,HoleType.LEFTTOP))
holeList.append(HolePosition(-18,21,HoleType.RIGHTBOTTOM))
holeList.append(HolePosition(-21,-18,HoleType.LEFTBOTTOM))
holeList.append(HolePosition(-18,-21,HoleType.LEFTBOTTOM))
holeList.append(HolePosition(21,19,HoleType.RIGHTTOP))
holeList.append(HolePosition(19,21,HoleType.RIGHTTOP))
holeList.append(HolePosition(-21,19,HoleType.RIGHTBOTTOM))
holeList.append(HolePosition(19,-21,HoleType.LEFTTOP))
holeList.append(HolePosition(21,-19,HoleType.LEFTTOP))
holeList.append(HolePosition(-19,21,HoleType.RIGHTBOTTOM))
holeList.append(HolePosition(-21,-19,HoleType.LEFTBOTTOM))
holeList.append(HolePosition(-19,-21,HoleType.LEFTBOTTOM))
holeList.append(HolePosition(22,0,HoleType.TOP))
holeList.append(HolePosition(0,22,HoleType.TOP))
holeList.append(HolePosition(-22,0,HoleType.BOTTOM))
holeList.append(HolePosition(0,-22,HoleType.BOTTOM))
holeList.append(HolePosition(22,1,HoleType.RIGHTTOP))
holeList.append(HolePosition(1,22,HoleType.RIGHTTOP))
holeList.append(HolePosition(-22,1,HoleType.RIGHTBOTTOM))
holeList.append(HolePosition(1,-22,HoleType.LEFTTOP))
holeList.append(HolePosition(22,-1,HoleType.LEFTTOP))
holeList.append(HolePosition(-1,22,HoleType.RIGHTBOTTOM))
holeList.append(HolePosition(-22,-1,HoleType.LEFTBOTTOM))
holeList.append(HolePosition(-1,-22,HoleType.LEFTBOTTOM))
holeList.append(HolePosition(22,2,HoleType.RIGHTTOP))
holeList.append(HolePosition(2,22,HoleType.RIGHTTOP))
holeList.append(HolePosition(-22,2,HoleType.RIGHTBOTTOM))
holeList.append(HolePosition(2,-22,HoleType.LEFTTOP))
holeList.append(HolePosition(22,-2,HoleType.LEFTTOP))
holeList.append(HolePosition(-2,22,HoleType.RIGHTBOTTOM))
holeList.append(HolePosition(-22,-2,HoleType.LEFTBOTTOM))
holeList.append(HolePosition(-2,-22,HoleType.LEFTBOTTOM))
holeList.append(HolePosition(22,3,HoleType.RIGHTTOP))
holeList.append(HolePosition(3,22,HoleType.RIGHTTOP))
holeList.append(HolePosition(-22,3,HoleType.RIGHTBOTTOM))
holeList.append(HolePosition(3,-22,HoleType.LEFTTOP))
holeList.append(HolePosition(22,-3,HoleType.LEFTTOP))
holeList.append(HolePosition(-3,22,HoleType.RIGHTBOTTOM))
holeList.append(HolePosition(-22,-3,HoleType.LEFTBOTTOM))
holeList.append(HolePosition(-3,-22,HoleType.LEFTBOTTOM))
holeList.append(HolePosition(22,4,HoleType.RIGHTTOP))
holeList.append(HolePosition(4,22,HoleType.RIGHTTOP))
holeList.append(HolePosition(-22,4,HoleType.RIGHTBOTTOM))
holeList.append(HolePosition(4,-22,HoleType.LEFTTOP))
holeList.append(HolePosition(22,-4,HoleType.LEFTTOP))
holeList.append(HolePosition(-4,22,HoleType.RIGHTBOTTOM))
holeList.append(HolePosition(-22,-4,HoleType.LEFTBOTTOM))
holeList.append(HolePosition(-4,-22,HoleType.LEFTBOTTOM))
holeList.append(HolePosition(22,5,HoleType.RIGHTTOP))
holeList.append(HolePosition(5,22,HoleType.RIGHTTOP))
holeList.append(HolePosition(-22,5,HoleType.RIGHTBOTTOM))
holeList.append(HolePosition(5,-22,HoleType.LEFTTOP))
holeList.append(HolePosition(22,-5,HoleType.LEFTTOP))
holeList.append(HolePosition(-5,22,HoleType.RIGHTBOTTOM))
holeList.append(HolePosition(-22,-5,HoleType.LEFTBOTTOM))
holeList.append(HolePosition(-5,-22,HoleType.LEFTBOTTOM))
holeList.append(HolePosition(22,6,HoleType.RIGHTTOP))
holeList.append(HolePosition(6,22,HoleType.RIGHTTOP))
holeList.append(HolePosition(-22,6,HoleType.RIGHTBOTTOM))
holeList.append(HolePosition(6,-22,HoleType.LEFTTOP))
holeList.append(HolePosition(22,-6,HoleType.LEFTTOP))
holeList.append(HolePosition(-6,22,HoleType.RIGHTBOTTOM))
holeList.append(HolePosition(-22,-6,HoleType.LEFTBOTTOM))
holeList.append(HolePosition(-6,-22,HoleType.LEFTBOTTOM))
holeList.append(HolePosition(22,7,HoleType.RIGHTTOP))
holeList.append(HolePosition(7,22,HoleType.RIGHTTOP))
holeList.append(HolePosition(-22,7,HoleType.RIGHTBOTTOM))
holeList.append(HolePosition(7,-22,HoleType.LEFTTOP))
holeList.append(HolePosition(22,-7,HoleType.LEFTTOP))
holeList.append(HolePosition(-7,22,HoleType.RIGHTBOTTOM))
holeList.append(HolePosition(-22,-7,HoleType.LEFTBOTTOM))
holeList.append(HolePosition(-7,-22,HoleType.LEFTBOTTOM))
holeList.append(HolePosition(22,8,HoleType.RIGHTTOP))
holeList.append(HolePosition(8,22,HoleType.RIGHTTOP))
holeList.append(HolePosition(-22,8,HoleType.RIGHTBOTTOM))
holeList.append(HolePosition(8,-22,HoleType.LEFTTOP))
holeList.append(HolePosition(22,-8,HoleType.LEFTTOP))
holeList.append(HolePosition(-8,22,HoleType.RIGHTBOTTOM))
holeList.append(HolePosition(-22,-8,HoleType.LEFTBOTTOM))
holeList.append(HolePosition(-8,-22,HoleType.LEFTBOTTOM))
holeList.append(HolePosition(22,9,HoleType.RIGHTTOP))
holeList.append(HolePosition(9,22,HoleType.RIGHTTOP))
holeList.append(HolePosition(-22,9,HoleType.RIGHTBOTTOM))
holeList.append(HolePosition(9,-22,HoleType.LEFTTOP))
holeList.append(HolePosition(22,-9,HoleType.LEFTTOP))
holeList.append(HolePosition(-9,22,HoleType.RIGHTBOTTOM))
holeList.append(HolePosition(-22,-9,HoleType.LEFTBOTTOM))
holeList.append(HolePosition(-9,-22,HoleType.LEFTBOTTOM))
holeList.append(HolePosition(22,10,HoleType.RIGHTTOP))
holeList.append(HolePosition(10,22,HoleType.RIGHTTOP))
holeList.append(HolePosition(-22,10,HoleType.RIGHTBOTTOM))
holeList.append(HolePosition(10,-22,HoleType.LEFTTOP))
holeList.append(HolePosition(22,-10,HoleType.LEFTTOP))
holeList.append(HolePosition(-10,22,HoleType.RIGHTBOTTOM))
holeList.append(HolePosition(-22,-10,HoleType.LEFTBOTTOM))
holeList.append(HolePosition(-10,-22,HoleType.LEFTBOTTOM))
holeList.append(HolePosition(22,11,HoleType.RIGHTTOP))
holeList.append(HolePosition(11,22,HoleType.RIGHTTOP))
holeList.append(HolePosition(-22,11,HoleType.RIGHTBOTTOM))
holeList.append(HolePosition(11,-22,HoleType.LEFTTOP))
holeList.append(HolePosition(22,-11,HoleType.LEFTTOP))
holeList.append(HolePosition(-11,22,HoleType.RIGHTBOTTOM))
holeList.append(HolePosition(-22,-11,HoleType.LEFTBOTTOM))
holeList.append(HolePosition(-11,-22,HoleType.LEFTBOTTOM))
holeList.append(HolePosition(22,12,HoleType.RIGHTTOP))
holeList.append(HolePosition(12,22,HoleType.RIGHTTOP))
holeList.append(HolePosition(-22,12,HoleType.RIGHTBOTTOM))
holeList.append(HolePosition(12,-22,HoleType.LEFTTOP))
holeList.append(HolePosition(22,-12,HoleType.LEFTTOP))
holeList.append(HolePosition(-12,22,HoleType.RIGHTBOTTOM))
holeList.append(HolePosition(-22,-12,HoleType.LEFTBOTTOM))
holeList.append(HolePosition(-12,-22,HoleType.LEFTBOTTOM))
holeList.append(HolePosition(22,13,HoleType.RIGHTTOP))
holeList.append(HolePosition(13,22,HoleType.RIGHTTOP))
holeList.append(HolePosition(-22,13,HoleType.RIGHTBOTTOM))
holeList.append(HolePosition(13,-22,HoleType.LEFTTOP))
holeList.append(HolePosition(22,-13,HoleType.LEFTTOP))
holeList.append(HolePosition(-13,22,HoleType.RIGHTBOTTOM))
holeList.append(HolePosition(-22,-13,HoleType.LEFTBOTTOM))
holeList.append(HolePosition(-13,-22,HoleType.LEFTBOTTOM))
holeList.append(HolePosition(22,14,HoleType.RIGHTTOP))
holeList.append(HolePosition(14,22,HoleType.RIGHTTOP))
holeList.append(HolePosition(-22,14,HoleType.RIGHTBOTTOM))
holeList.append(HolePosition(14,-22,HoleType.LEFTTOP))
holeList.append(HolePosition(22,-14,HoleType.LEFTTOP))
holeList.append(HolePosition(-14,22,HoleType.RIGHTBOTTOM))
holeList.append(HolePosition(-22,-14,HoleType.LEFTBOTTOM))
holeList.append(HolePosition(-14,-22,HoleType.LEFTBOTTOM))
holeList.append(HolePosition(22,15,HoleType.RIGHTTOP))
holeList.append(HolePosition(15,22,HoleType.RIGHTTOP))
holeList.append(HolePosition(-22,15,HoleType.RIGHTBOTTOM))
holeList.append(HolePosition(15,-22,HoleType.LEFTTOP))
holeList.append(HolePosition(22,-15,HoleType.LEFTTOP))
holeList.append(HolePosition(-15,22,HoleType.RIGHTBOTTOM))
holeList.append(HolePosition(-22,-15,HoleType.LEFTBOTTOM))
holeList.append(HolePosition(-15,-22,HoleType.LEFTBOTTOM))
holeList.append(HolePosition(22,16,HoleType.RIGHTTOP))
holeList.append(HolePosition(16,22,HoleType.RIGHTTOP))
holeList.append(HolePosition(-22,16,HoleType.RIGHTBOTTOM))
holeList.append(HolePosition(16,-22,HoleType.LEFTTOP))
holeList.append(HolePosition(22,-16,HoleType.LEFTTOP))
holeList.append(HolePosition(-16,22,HoleType.RIGHTBOTTOM))
holeList.append(HolePosition(-22,-16,HoleType.LEFTBOTTOM))
holeList.append(HolePosition(-16,-22,HoleType.LEFTBOTTOM))
holeList.append(HolePosition(22,17,HoleType.RIGHTTOP))
holeList.append(HolePosition(17,22,HoleType.RIGHTTOP))
holeList.append(HolePosition(-22,17,HoleType.RIGHTBOTTOM))
holeList.append(HolePosition(17,-22,HoleType.LEFTTOP))
holeList.append(HolePosition(22,-17,HoleType.LEFTTOP))
holeList.append(HolePosition(-17,22,HoleType.RIGHTBOTTOM))
holeList.append(HolePosition(-22,-17,HoleType.LEFTBOTTOM))
holeList.append(HolePosition(-17,-22,HoleType.LEFTBOTTOM))
holeList.append(HolePosition(23,0,HoleType.TOP))
holeList.append(HolePosition(0,23,HoleType.TOP))
holeList.append(HolePosition(-23,0,HoleType.BOTTOM))
holeList.append(HolePosition(0,-23,HoleType.BOTTOM))
holeList.append(HolePosition(23,1,HoleType.RIGHTTOP))
holeList.append(HolePosition(1,23,HoleType.RIGHTTOP))
holeList.append(HolePosition(-23,1,HoleType.RIGHTBOTTOM))
holeList.append(HolePosition(1,-23,HoleType.LEFTTOP))
holeList.append(HolePosition(23,-1,HoleType.LEFTTOP))
holeList.append(HolePosition(-1,23,HoleType.RIGHTBOTTOM))
holeList.append(HolePosition(-23,-1,HoleType.LEFTBOTTOM))
holeList.append(HolePosition(-1,-23,HoleType.LEFTBOTTOM))
holeList.append(HolePosition(23,2,HoleType.RIGHTTOP))
holeList.append(HolePosition(2,23,HoleType.RIGHTTOP))
holeList.append(HolePosition(-23,2,HoleType.RIGHTBOTTOM))
holeList.append(HolePosition(2,-23,HoleType.LEFTTOP))
holeList.append(HolePosition(23,-2,HoleType.LEFTTOP))
holeList.append(HolePosition(-2,23,HoleType.RIGHTBOTTOM))
holeList.append(HolePosition(-23,-2,HoleType.LEFTBOTTOM))
holeList.append(HolePosition(-2,-23,HoleType.LEFTBOTTOM))
holeList.append(HolePosition(23,3,HoleType.RIGHTTOP))
holeList.append(HolePosition(3,23,HoleType.RIGHTTOP))
holeList.append(HolePosition(-23,3,HoleType.RIGHTBOTTOM))
holeList.append(HolePosition(3,-23,HoleType.LEFTTOP))
holeList.append(HolePosition(23,-3,HoleType.LEFTTOP))
holeList.append(HolePosition(-3,23,HoleType.RIGHTBOTTOM))
holeList.append(HolePosition(-23,-3,HoleType.LEFTBOTTOM))
holeList.append(HolePosition(-3,-23,HoleType.LEFTBOTTOM))
holeList.append(HolePosition(23,4,HoleType.RIGHTTOP))
holeList.append(HolePosition(4,23,HoleType.RIGHTTOP))
holeList.append(HolePosition(-23,4,HoleType.RIGHTBOTTOM))
holeList.append(HolePosition(4,-23,HoleType.LEFTTOP))
holeList.append(HolePosition(23,-4,HoleType.LEFTTOP))
holeList.append(HolePosition(-4,23,HoleType.RIGHTBOTTOM))
holeList.append(HolePosition(-23,-4,HoleType.LEFTBOTTOM))
holeList.append(HolePosition(-4,-23,HoleType.LEFTBOTTOM))
holeList.append(HolePosition(23,5,HoleType.RIGHTTOP))
holeList.append(HolePosition(5,23,HoleType.RIGHTTOP))
holeList.append(HolePosition(-23,5,HoleType.RIGHTBOTTOM))
holeList.append(HolePosition(5,-23,HoleType.LEFTTOP))
holeList.append(HolePosition(23,-5,HoleType.LEFTTOP))
holeList.append(HolePosition(-5,23,HoleType.RIGHTBOTTOM))
holeList.append(HolePosition(-23,-5,HoleType.LEFTBOTTOM))
holeList.append(HolePosition(-5,-23,HoleType.LEFTBOTTOM))
holeList.append(HolePosition(23,6,HoleType.RIGHTTOP))
holeList.append(HolePosition(6,23,HoleType.RIGHTTOP))
holeList.append(HolePosition(-23,6,HoleType.RIGHTBOTTOM))
holeList.append(HolePosition(6,-23,HoleType.LEFTTOP))
holeList.append(HolePosition(23,-6,HoleType.LEFTTOP))
holeList.append(HolePosition(-6,23,HoleType.RIGHTBOTTOM))
holeList.append(HolePosition(-23,-6,HoleType.LEFTBOTTOM))
holeList.append(HolePosition(-6,-23,HoleType.LEFTBOTTOM))
holeList.append(HolePosition(23,7,HoleType.RIGHTTOP))
holeList.append(HolePosition(7,23,HoleType.RIGHTTOP))
holeList.append(HolePosition(-23,7,HoleType.RIGHTBOTTOM))
holeList.append(HolePosition(7,-23,HoleType.LEFTTOP))
holeList.append(HolePosition(23,-7,HoleType.LEFTTOP))
holeList.append(HolePosition(-7,23,HoleType.RIGHTBOTTOM))
holeList.append(HolePosition(-23,-7,HoleType.LEFTBOTTOM))
holeList.append(HolePosition(-7,-23,HoleType.LEFTBOTTOM))
holeList.append(HolePosition(23,8,HoleType.RIGHTTOP))
holeList.append(HolePosition(8,23,HoleType.RIGHTTOP))
holeList.append(HolePosition(-23,8,HoleType.RIGHTBOTTOM))
holeList.append(HolePosition(8,-23,HoleType.LEFTTOP))
holeList.append(HolePosition(23,-8,HoleType.LEFTTOP))
holeList.append(HolePosition(-8,23,HoleType.RIGHTBOTTOM))
holeList.append(HolePosition(-23,-8,HoleType.LEFTBOTTOM))
holeList.append(HolePosition(-8,-23,HoleType.LEFTBOTTOM))
holeList.append(HolePosition(23,9,HoleType.RIGHTTOP))
holeList.append(HolePosition(9,23,HoleType.RIGHTTOP))
holeList.append(HolePosition(-23,9,HoleType.RIGHTBOTTOM))
holeList.append(HolePosition(9,-23,HoleType.LEFTTOP))
holeList.append(HolePosition(23,-9,HoleType.LEFTTOP))
holeList.append(HolePosition(-9,23,HoleType.RIGHTBOTTOM))
holeList.append(HolePosition(-23,-9,HoleType.LEFTBOTTOM))
holeList.append(HolePosition(-9,-23,HoleType.LEFTBOTTOM))
holeList.append(HolePosition(23,10,HoleType.RIGHTTOP))
holeList.append(HolePosition(10,23,HoleType.RIGHTTOP))
holeList.append(HolePosition(-23,10,HoleType.RIGHTBOTTOM))
holeList.append(HolePosition(10,-23,HoleType.LEFTTOP))
holeList.append(HolePosition(23,-10,HoleType.LEFTTOP))
holeList.append(HolePosition(-10,23,HoleType.RIGHTBOTTOM))
holeList.append(HolePosition(-23,-10,HoleType.LEFTBOTTOM))
holeList.append(HolePosition(-10,-23,HoleType.LEFTBOTTOM))
holeList.append(HolePosition(23,11,HoleType.RIGHTTOP))
holeList.append(HolePosition(11,23,HoleType.RIGHTTOP))
holeList.append(HolePosition(-23,11,HoleType.RIGHTBOTTOM))
holeList.append(HolePosition(11,-23,HoleType.LEFTTOP))
holeList.append(HolePosition(23,-11,HoleType.LEFTTOP))
holeList.append(HolePosition(-11,23,HoleType.RIGHTBOTTOM))
holeList.append(HolePosition(-23,-11,HoleType.LEFTBOTTOM))
holeList.append(HolePosition(-11,-23,HoleType.LEFTBOTTOM))
holeList.append(HolePosition(23,12,HoleType.RIGHTTOP))
holeList.append(HolePosition(12,23,HoleType.RIGHTTOP))
holeList.append(HolePosition(-23,12,HoleType.RIGHTBOTTOM))
holeList.append(HolePosition(12,-23,HoleType.LEFTTOP))
holeList.append(HolePosition(23,-12,HoleType.LEFTTOP))
holeList.append(HolePosition(-12,23,HoleType.RIGHTBOTTOM))
holeList.append(HolePosition(-23,-12,HoleType.LEFTBOTTOM))
holeList.append(HolePosition(-12,-23,HoleType.LEFTBOTTOM))
holeList.append(HolePosition(23,13,HoleType.RIGHTTOP))
holeList.append(HolePosition(13,23,HoleType.RIGHTTOP))
holeList.append(HolePosition(-23,13,HoleType.RIGHTBOTTOM))
holeList.append(HolePosition(13,-23,HoleType.LEFTTOP))
holeList.append(HolePosition(23,-13,HoleType.LEFTTOP))
holeList.append(HolePosition(-13,23,HoleType.RIGHTBOTTOM))
holeList.append(HolePosition(-23,-13,HoleType.LEFTBOTTOM))
holeList.append(HolePosition(-13,-23,HoleType.LEFTBOTTOM))
holeList.append(HolePosition(23,14,HoleType.RIGHTTOP))
holeList.append(HolePosition(14,23,HoleType.RIGHTTOP))
holeList.append(HolePosition(-23,14,HoleType.RIGHTBOTTOM))
holeList.append(HolePosition(14,-23,HoleType.LEFTTOP))
holeList.append(HolePosition(23,-14,HoleType.LEFTTOP))
holeList.append(HolePosition(-14,23,HoleType.RIGHTBOTTOM))
holeList.append(HolePosition(-23,-14,HoleType.LEFTBOTTOM))
holeList.append(HolePosition(-14,-23,HoleType.LEFTBOTTOM))
holeList.append(HolePosition(23,15,HoleType.RIGHTTOP))
holeList.append(HolePosition(15,23,HoleType.RIGHTTOP))
holeList.append(HolePosition(-23,15,HoleType.RIGHTBOTTOM))
holeList.append(HolePosition(15,-23,HoleType.LEFTTOP))
holeList.append(HolePosition(23,-15,HoleType.LEFTTOP))
holeList.append(HolePosition(-15,23,HoleType.RIGHTBOTTOM))
holeList.append(HolePosition(-23,-15,HoleType.LEFTBOTTOM))
holeList.append(HolePosition(-15,-23,HoleType.LEFTBOTTOM))
holeList.append(HolePosition(23,16,HoleType.RIGHTTOP))
holeList.append(HolePosition(16,23,HoleType.RIGHTTOP))
holeList.append(HolePosition(-23,16,HoleType.RIGHTBOTTOM))
holeList.append(HolePosition(16,-23,HoleType.LEFTTOP))
holeList.append(HolePosition(23,-16,HoleType.LEFTTOP))
holeList.append(HolePosition(-16,23,HoleType.RIGHTBOTTOM))
holeList.append(HolePosition(-23,-16,HoleType.LEFTBOTTOM))
holeList.append(HolePosition(-16,-23,HoleType.LEFTBOTTOM))
holeList.append(HolePosition(24,0,HoleType.TOP))
holeList.append(HolePosition(0,24,HoleType.TOP))
holeList.append(HolePosition(-24,0,HoleType.BOTTOM))
holeList.append(HolePosition(0,-24,HoleType.BOTTOM))
holeList.append(HolePosition(24,1,HoleType.RIGHTTOP))
holeList.append(HolePosition(1,24,HoleType.RIGHTTOP))
holeList.append(HolePosition(-24,1,HoleType.RIGHTBOTTOM))
holeList.append(HolePosition(1,-24,HoleType.LEFTTOP))
holeList.append(HolePosition(24,-1,HoleType.LEFTTOP))
holeList.append(HolePosition(-1,24,HoleType.RIGHTBOTTOM))
holeList.append(HolePosition(-24,-1,HoleType.LEFTBOTTOM))
holeList.append(HolePosition(-1,-24,HoleType.LEFTBOTTOM))
holeList.append(HolePosition(24,2,HoleType.RIGHTTOP))
holeList.append(HolePosition(2,24,HoleType.RIGHTTOP))
holeList.append(HolePosition(-24,2,HoleType.RIGHTBOTTOM))
holeList.append(HolePosition(2,-24,HoleType.LEFTTOP))
holeList.append(HolePosition(24,-2,HoleType.LEFTTOP))
holeList.append(HolePosition(-2,24,HoleType.RIGHTBOTTOM))
holeList.append(HolePosition(-24,-2,HoleType.LEFTBOTTOM))
holeList.append(HolePosition(-2,-24,HoleType.LEFTBOTTOM))
holeList.append(HolePosition(24,3,HoleType.RIGHTTOP))
holeList.append(HolePosition(3,24,HoleType.RIGHTTOP))
holeList.append(HolePosition(-24,3,HoleType.RIGHTBOTTOM))
holeList.append(HolePosition(3,-24,HoleType.LEFTTOP))
holeList.append(HolePosition(24,-3,HoleType.LEFTTOP))
holeList.append(HolePosition(-3,24,HoleType.RIGHTBOTTOM))
holeList.append(HolePosition(-24,-3,HoleType.LEFTBOTTOM))
holeList.append(HolePosition(-3,-24,HoleType.LEFTBOTTOM))
holeList.append(HolePosition(24,4,HoleType.RIGHTTOP))
holeList.append(HolePosition(4,24,HoleType.RIGHTTOP))
holeList.append(HolePosition(-24,4,HoleType.RIGHTBOTTOM))
holeList.append(HolePosition(4,-24,HoleType.LEFTTOP))
holeList.append(HolePosition(24,-4,HoleType.LEFTTOP))
holeList.append(HolePosition(-4,24,HoleType.RIGHTBOTTOM))
holeList.append(HolePosition(-24,-4,HoleType.LEFTBOTTOM))
holeList.append(HolePosition(-4,-24,HoleType.LEFTBOTTOM))
holeList.append(HolePosition(24,5,HoleType.RIGHTTOP))
holeList.append(HolePosition(5,24,HoleType.RIGHTTOP))
holeList.append(HolePosition(-24,5,HoleType.RIGHTBOTTOM))
holeList.append(HolePosition(5,-24,HoleType.LEFTTOP))
holeList.append(HolePosition(24,-5,HoleType.LEFTTOP))
holeList.append(HolePosition(-5,24,HoleType.RIGHTBOTTOM))
holeList.append(HolePosition(-24,-5,HoleType.LEFTBOTTOM))
holeList.append(HolePosition(-5,-24,HoleType.LEFTBOTTOM))
holeList.append(HolePosition(24,6,HoleType.RIGHTTOP))
holeList.append(HolePosition(6,24,HoleType.RIGHTTOP))
holeList.append(HolePosition(-24,6,HoleType.RIGHTBOTTOM))
holeList.append(HolePosition(6,-24,HoleType.LEFTTOP))
holeList.append(HolePosition(24,-6,HoleType.LEFTTOP))
holeList.append(HolePosition(-6,24,HoleType.RIGHTBOTTOM))
holeList.append(HolePosition(-24,-6,HoleType.LEFTBOTTOM))
holeList.append(HolePosition(-6,-24,HoleType.LEFTBOTTOM))
holeList.append(HolePosition(24,7,HoleType.RIGHTTOP))
holeList.append(HolePosition(7,24,HoleType.RIGHTTOP))
holeList.append(HolePosition(-24,7,HoleType.RIGHTBOTTOM))
holeList.append(HolePosition(7,-24,HoleType.LEFTTOP))
holeList.append(HolePosition(24,-7,HoleType.LEFTTOP))
holeList.append(HolePosition(-7,24,HoleType.RIGHTBOTTOM))
holeList.append(HolePosition(-24,-7,HoleType.LEFTBOTTOM))
holeList.append(HolePosition(-7,-24,HoleType.LEFTBOTTOM))
holeList.append(HolePosition(24,8,HoleType.RIGHTTOP))
holeList.append(HolePosition(8,24,HoleType.RIGHTTOP))
holeList.append(HolePosition(-24,8,HoleType.RIGHTBOTTOM))
holeList.append(HolePosition(8,-24,HoleType.LEFTTOP))
holeList.append(HolePosition(24,-8,HoleType.LEFTTOP))
holeList.append(HolePosition(-8,24,HoleType.RIGHTBOTTOM))
holeList.append(HolePosition(-24,-8,HoleType.LEFTBOTTOM))
holeList.append(HolePosition(-8,-24,HoleType.LEFTBOTTOM))
holeList.append(HolePosition(24,9,HoleType.RIGHTTOP))
holeList.append(HolePosition(9,24,HoleType.RIGHTTOP))
holeList.append(HolePosition(-24,9,HoleType.RIGHTBOTTOM))
holeList.append(HolePosition(9,-24,HoleType.LEFTTOP))
holeList.append(HolePosition(24,-9,HoleType.LEFTTOP))
holeList.append(HolePosition(-9,24,HoleType.RIGHTBOTTOM))
holeList.append(HolePosition(-24,-9,HoleType.LEFTBOTTOM))
holeList.append(HolePosition(-9,-24,HoleType.LEFTBOTTOM))
holeList.append(HolePosition(24,10,HoleType.RIGHTTOP))
holeList.append(HolePosition(10,24,HoleType.RIGHTTOP))
holeList.append(HolePosition(-24,10,HoleType.RIGHTBOTTOM))
holeList.append(HolePosition(10,-24,HoleType.LEFTTOP))
holeList.append(HolePosition(24,-10,HoleType.LEFTTOP))
holeList.append(HolePosition(-10,24,HoleType.RIGHTBOTTOM))
holeList.append(HolePosition(-24,-10,HoleType.LEFTBOTTOM))
holeList.append(HolePosition(-10,-24,HoleType.LEFTBOTTOM))
holeList.append(HolePosition(24,11,HoleType.RIGHTTOP))
holeList.append(HolePosition(11,24,HoleType.RIGHTTOP))
holeList.append(HolePosition(-24,11,HoleType.RIGHTBOTTOM))
holeList.append(HolePosition(11,-24,HoleType.LEFTTOP))
holeList.append(HolePosition(24,-11,HoleType.LEFTTOP))
holeList.append(HolePosition(-11,24,HoleType.RIGHTBOTTOM))
holeList.append(HolePosition(-24,-11,HoleType.LEFTBOTTOM))
holeList.append(HolePosition(-11,-24,HoleType.LEFTBOTTOM))
holeList.append(HolePosition(24,12,HoleType.RIGHTTOP))
holeList.append(HolePosition(12,24,HoleType.RIGHTTOP))
holeList.append(HolePosition(-24,12,HoleType.RIGHTBOTTOM))
holeList.append(HolePosition(12,-24,HoleType.LEFTTOP))
holeList.append(HolePosition(24,-12,HoleType.LEFTTOP))
holeList.append(HolePosition(-12,24,HoleType.RIGHTBOTTOM))
holeList.append(HolePosition(-24,-12,HoleType.LEFTBOTTOM))
holeList.append(HolePosition(-12,-24,HoleType.LEFTBOTTOM))
holeList.append(HolePosition(24,13,HoleType.RIGHTTOP))
holeList.append(HolePosition(13,24,HoleType.RIGHTTOP))
holeList.append(HolePosition(-24,13,HoleType.RIGHTBOTTOM))
holeList.append(HolePosition(13,-24,HoleType.LEFTTOP))
holeList.append(HolePosition(24,-13,HoleType.LEFTTOP))
holeList.append(HolePosition(-13,24,HoleType.RIGHTBOTTOM))
holeList.append(HolePosition(-24,-13,HoleType.LEFTBOTTOM))
holeList.append(HolePosition(-13,-24,HoleType.LEFTBOTTOM))
holeList.append(HolePosition(24,14,HoleType.RIGHTTOP))
holeList.append(HolePosition(14,24,HoleType.RIGHTTOP))
holeList.append(HolePosition(-24,14,HoleType.RIGHTBOTTOM))
holeList.append(HolePosition(14,-24,HoleType.LEFTTOP))
holeList.append(HolePosition(24,-14,HoleType.LEFTTOP))
holeList.append(HolePosition(-14,24,HoleType.RIGHTBOTTOM))
holeList.append(HolePosition(-24,-14,HoleType.LEFTBOTTOM))
holeList.append(HolePosition(-14,-24,HoleType.LEFTBOTTOM))
holeList.append(HolePosition(24,15,HoleType.RIGHTTOP))
holeList.append(HolePosition(15,24,HoleType.RIGHTTOP))
holeList.append(HolePosition(-24,15,HoleType.RIGHTBOTTOM))
holeList.append(HolePosition(15,-24,HoleType.LEFTTOP))
holeList.append(HolePosition(24,-15,HoleType.LEFTTOP))
holeList.append(HolePosition(-15,24,HoleType.RIGHTBOTTOM))
holeList.append(HolePosition(-24,-15,HoleType.LEFTBOTTOM))
holeList.append(HolePosition(-15,-24,HoleType.LEFTBOTTOM))
holeList.append(HolePosition(25,0,HoleType.TOP))
holeList.append(HolePosition(0,25,HoleType.TOP))
holeList.append(HolePosition(-25,0,HoleType.BOTTOM))
holeList.append(HolePosition(0,-25,HoleType.BOTTOM))
holeList.append(HolePosition(25,1,HoleType.RIGHTTOP))
holeList.append(HolePosition(1,25,HoleType.RIGHTTOP))
holeList.append(HolePosition(-25,1,HoleType.RIGHTBOTTOM))
holeList.append(HolePosition(1,-25,HoleType.LEFTTOP))
holeList.append(HolePosition(25,-1,HoleType.LEFTTOP))
holeList.append(HolePosition(-1,25,HoleType.RIGHTBOTTOM))
holeList.append(HolePosition(-25,-1,HoleType.LEFTBOTTOM))
holeList.append(HolePosition(-1,-25,HoleType.LEFTBOTTOM))
holeList.append(HolePosition(25,2,HoleType.RIGHTTOP))
holeList.append(HolePosition(2,25,HoleType.RIGHTTOP))
holeList.append(HolePosition(-25,2,HoleType.RIGHTBOTTOM))
holeList.append(HolePosition(2,-25,HoleType.LEFTTOP))
holeList.append(HolePosition(25,-2,HoleType.LEFTTOP))
holeList.append(HolePosition(-2,25,HoleType.RIGHTBOTTOM))
holeList.append(HolePosition(-25,-2,HoleType.LEFTBOTTOM))
holeList.append(HolePosition(-2,-25,HoleType.LEFTBOTTOM))
holeList.append(HolePosition(25,3,HoleType.RIGHTTOP))
holeList.append(HolePosition(3,25,HoleType.RIGHTTOP))
holeList.append(HolePosition(-25,3,HoleType.RIGHTBOTTOM))
holeList.append(HolePosition(3,-25,HoleType.LEFTTOP))
holeList.append(HolePosition(25,-3,HoleType.LEFTTOP))
holeList.append(HolePosition(-3,25,HoleType.RIGHTBOTTOM))
holeList.append(HolePosition(-25,-3,HoleType.LEFTBOTTOM))
holeList.append(HolePosition(-3,-25,HoleType.LEFTBOTTOM))
holeList.append(HolePosition(25,4,HoleType.RIGHTTOP))
holeList.append(HolePosition(4,25,HoleType.RIGHTTOP))
holeList.append(HolePosition(-25,4,HoleType.RIGHTBOTTOM))
holeList.append(HolePosition(4,-25,HoleType.LEFTTOP))
holeList.append(HolePosition(25,-4,HoleType.LEFTTOP))
holeList.append(HolePosition(-4,25,HoleType.RIGHTBOTTOM))
holeList.append(HolePosition(-25,-4,HoleType.LEFTBOTTOM))
holeList.append(HolePosition(-4,-25,HoleType.LEFTBOTTOM))
holeList.append(HolePosition(25,5,HoleType.RIGHTTOP))
holeList.append(HolePosition(5,25,HoleType.RIGHTTOP))
holeList.append(HolePosition(-25,5,HoleType.RIGHTBOTTOM))
holeList.append(HolePosition(5,-25,HoleType.LEFTTOP))
holeList.append(HolePosition(25,-5,HoleType.LEFTTOP))
holeList.append(HolePosition(-5,25,HoleType.RIGHTBOTTOM))
holeList.append(HolePosition(-25,-5,HoleType.LEFTBOTTOM))
holeList.append(HolePosition(-5,-25,HoleType.LEFTBOTTOM))
holeList.append(HolePosition(25,6,HoleType.RIGHTTOP))
holeList.append(HolePosition(6,25,HoleType.RIGHTTOP))
holeList.append(HolePosition(-25,6,HoleType.RIGHTBOTTOM))
holeList.append(HolePosition(6,-25,HoleType.LEFTTOP))
holeList.append(HolePosition(25,-6,HoleType.LEFTTOP))
holeList.append(HolePosition(-6,25,HoleType.RIGHTBOTTOM))
holeList.append(HolePosition(-25,-6,HoleType.LEFTBOTTOM))
holeList.append(HolePosition(-6,-25,HoleType.LEFTBOTTOM))
holeList.append(HolePosition(25,7,HoleType.RIGHTTOP))
holeList.append(HolePosition(7,25,HoleType.RIGHTTOP))
holeList.append(HolePosition(-25,7,HoleType.RIGHTBOTTOM))
holeList.append(HolePosition(7,-25,HoleType.LEFTTOP))
holeList.append(HolePosition(25,-7,HoleType.LEFTTOP))
holeList.append(HolePosition(-7,25,HoleType.RIGHTBOTTOM))
holeList.append(HolePosition(-25,-7,HoleType.LEFTBOTTOM))
holeList.append(HolePosition(-7,-25,HoleType.LEFTBOTTOM))
holeList.append(HolePosition(25,8,HoleType.RIGHTTOP))
holeList.append(HolePosition(8,25,HoleType.RIGHTTOP))
holeList.append(HolePosition(-25,8,HoleType.RIGHTBOTTOM))
holeList.append(HolePosition(8,-25,HoleType.LEFTTOP))
holeList.append(HolePosition(25,-8,HoleType.LEFTTOP))
holeList.append(HolePosition(-8,25,HoleType.RIGHTBOTTOM))
holeList.append(HolePosition(-25,-8,HoleType.LEFTBOTTOM))
holeList.append(HolePosition(-8,-25,HoleType.LEFTBOTTOM))
holeList.append(HolePosition(25,9,HoleType.RIGHTTOP))
holeList.append(HolePosition(9,25,HoleType.RIGHTTOP))
holeList.append(HolePosition(-25,9,HoleType.RIGHTBOTTOM))
holeList.append(HolePosition(9,-25,HoleType.LEFTTOP))
holeList.append(HolePosition(25,-9,HoleType.LEFTTOP))
holeList.append(HolePosition(-9,25,HoleType.RIGHTBOTTOM))
holeList.append(HolePosition(-25,-9,HoleType.LEFTBOTTOM))
holeList.append(HolePosition(-9,-25,HoleType.LEFTBOTTOM))
holeList.append(HolePosition(25,10,HoleType.RIGHTTOP))
holeList.append(HolePosition(10,25,HoleType.RIGHTTOP))
holeList.append(HolePosition(-25,10,HoleType.RIGHTBOTTOM))
holeList.append(HolePosition(10,-25,HoleType.LEFTTOP))
holeList.append(HolePosition(25,-10,HoleType.LEFTTOP))
holeList.append(HolePosition(-10,25,HoleType.RIGHTBOTTOM))
holeList.append(HolePosition(-25,-10,HoleType.LEFTBOTTOM))
holeList.append(HolePosition(-10,-25,HoleType.LEFTBOTTOM))
holeList.append(HolePosition(25,11,HoleType.RIGHTTOP))
holeList.append(HolePosition(11,25,HoleType.RIGHTTOP))
holeList.append(HolePosition(-25,11,HoleType.RIGHTBOTTOM))
holeList.append(HolePosition(11,-25,HoleType.LEFTTOP))
holeList.append(HolePosition(25,-11,HoleType.LEFTTOP))
holeList.append(HolePosition(-11,25,HoleType.RIGHTBOTTOM))
holeList.append(HolePosition(-25,-11,HoleType.LEFTBOTTOM))
holeList.append(HolePosition(-11,-25,HoleType.LEFTBOTTOM))
holeList.append(HolePosition(25,12,HoleType.RIGHTTOP))
holeList.append(HolePosition(12,25,HoleType.RIGHTTOP))
holeList.append(HolePosition(-25,12,HoleType.RIGHTBOTTOM))
holeList.append(HolePosition(12,-25,HoleType.LEFTTOP))
holeList.append(HolePosition(25,-12,HoleType.LEFTTOP))
holeList.append(HolePosition(-12,25,HoleType.RIGHTBOTTOM))
holeList.append(HolePosition(-25,-12,HoleType.LEFTBOTTOM))
holeList.append(HolePosition(-12,-25,HoleType.LEFTBOTTOM))
holeList.append(HolePosition(25,13,HoleType.RIGHTTOP))
holeList.append(HolePosition(13,25,HoleType.RIGHTTOP))
holeList.append(HolePosition(-25,13,HoleType.RIGHTBOTTOM))
holeList.append(HolePosition(13,-25,HoleType.LEFTTOP))
holeList.append(HolePosition(25,-13,HoleType.LEFTTOP))
holeList.append(HolePosition(-13,25,HoleType.RIGHTBOTTOM))
holeList.append(HolePosition(-25,-13,HoleType.LEFTBOTTOM))
holeList.append(HolePosition(-13,-25,HoleType.LEFTBOTTOM))
holeList.append(HolePosition(26,0,HoleType.TOP))
holeList.append(HolePosition(0,26,HoleType.TOP))
holeList.append(HolePosition(-26,0,HoleType.BOTTOM))
holeList.append(HolePosition(0,-26,HoleType.BOTTOM))
holeList.append(HolePosition(26,1,HoleType.RIGHTTOP))
holeList.append(HolePosition(1,26,HoleType.RIGHTTOP))
holeList.append(HolePosition(-26,1,HoleType.RIGHTBOTTOM))
holeList.append(HolePosition(1,-26,HoleType.LEFTTOP))
holeList.append(HolePosition(26,-1,HoleType.LEFTTOP))
holeList.append(HolePosition(-1,26,HoleType.RIGHTBOTTOM))
holeList.append(HolePosition(-26,-1,HoleType.LEFTBOTTOM))
holeList.append(HolePosition(-1,-26,HoleType.LEFTBOTTOM))
holeList.append(HolePosition(26,2,HoleType.RIGHTTOP))
holeList.append(HolePosition(2,26,HoleType.RIGHTTOP))
holeList.append(HolePosition(-26,2,HoleType.RIGHTBOTTOM))
holeList.append(HolePosition(2,-26,HoleType.LEFTTOP))
holeList.append(HolePosition(26,-2,HoleType.LEFTTOP))
holeList.append(HolePosition(-2,26,HoleType.RIGHTBOTTOM))
holeList.append(HolePosition(-26,-2,HoleType.LEFTBOTTOM))
holeList.append(HolePosition(-2,-26,HoleType.LEFTBOTTOM))
holeList.append(HolePosition(26,3,HoleType.RIGHTTOP))
holeList.append(HolePosition(3,26,HoleType.RIGHTTOP))
holeList.append(HolePosition(-26,3,HoleType.RIGHTBOTTOM))
holeList.append(HolePosition(3,-26,HoleType.LEFTTOP))
holeList.append(HolePosition(26,-3,HoleType.LEFTTOP))
holeList.append(HolePosition(-3,26,HoleType.RIGHTBOTTOM))
holeList.append(HolePosition(-26,-3,HoleType.LEFTBOTTOM))
holeList.append(HolePosition(-3,-26,HoleType.LEFTBOTTOM))
holeList.append(HolePosition(26,4,HoleType.RIGHTTOP))
holeList.append(HolePosition(4,26,HoleType.RIGHTTOP))
holeList.append(HolePosition(-26,4,HoleType.RIGHTBOTTOM))
holeList.append(HolePosition(4,-26,HoleType.LEFTTOP))
holeList.append(HolePosition(26,-4,HoleType.LEFTTOP))
holeList.append(HolePosition(-4,26,HoleType.RIGHTBOTTOM))
holeList.append(HolePosition(-26,-4,HoleType.LEFTBOTTOM))
holeList.append(HolePosition(-4,-26,HoleType.LEFTBOTTOM))
holeList.append(HolePosition(26,5,HoleType.RIGHTTOP))
holeList.append(HolePosition(5,26,HoleType.RIGHTTOP))
holeList.append(HolePosition(-26,5,HoleType.RIGHTBOTTOM))
holeList.append(HolePosition(5,-26,HoleType.LEFTTOP))
holeList.append(HolePosition(26,-5,HoleType.LEFTTOP))
holeList.append(HolePosition(-5,26,HoleType.RIGHTBOTTOM))
holeList.append(HolePosition(-26,-5,HoleType.LEFTBOTTOM))
holeList.append(HolePosition(-5,-26,HoleType.LEFTBOTTOM))
holeList.append(HolePosition(26,6,HoleType.RIGHTTOP))
holeList.append(HolePosition(6,26,HoleType.RIGHTTOP))
holeList.append(HolePosition(-26,6,HoleType.RIGHTBOTTOM))
holeList.append(HolePosition(6,-26,HoleType.LEFTTOP))
holeList.append(HolePosition(26,-6,HoleType.LEFTTOP))
holeList.append(HolePosition(-6,26,HoleType.RIGHTBOTTOM))
holeList.append(HolePosition(-26,-6,HoleType.LEFTBOTTOM))
holeList.append(HolePosition(-6,-26,HoleType.LEFTBOTTOM))
holeList.append(HolePosition(26,7,HoleType.RIGHTTOP))
holeList.append(HolePosition(7,26,HoleType.RIGHTTOP))
holeList.append(HolePosition(-26,7,HoleType.RIGHTBOTTOM))
holeList.append(HolePosition(7,-26,HoleType.LEFTTOP))
holeList.append(HolePosition(26,-7,HoleType.LEFTTOP))
holeList.append(HolePosition(-7,26,HoleType.RIGHTBOTTOM))
holeList.append(HolePosition(-26,-7,HoleType.LEFTBOTTOM))
holeList.append(HolePosition(-7,-26,HoleType.LEFTBOTTOM))
holeList.append(HolePosition(26,8,HoleType.RIGHTTOP))
holeList.append(HolePosition(8,26,HoleType.RIGHTTOP))
holeList.append(HolePosition(-26,8,HoleType.RIGHTBOTTOM))
holeList.append(HolePosition(8,-26,HoleType.LEFTTOP))
holeList.append(HolePosition(26,-8,HoleType.LEFTTOP))
holeList.append(HolePosition(-8,26,HoleType.RIGHTBOTTOM))
holeList.append(HolePosition(-26,-8,HoleType.LEFTBOTTOM))
holeList.append(HolePosition(-8,-26,HoleType.LEFTBOTTOM))
holeList.append(HolePosition(26,9,HoleType.RIGHTTOP))
holeList.append(HolePosition(9,26,HoleType.RIGHTTOP))
holeList.append(HolePosition(-26,9,HoleType.RIGHTBOTTOM))
holeList.append(HolePosition(9,-26,HoleType.LEFTTOP))
holeList.append(HolePosition(26,-9,HoleType.LEFTTOP))
holeList.append(HolePosition(-9,26,HoleType.RIGHTBOTTOM))
holeList.append(HolePosition(-26,-9,HoleType.LEFTBOTTOM))
holeList.append(HolePosition(-9,-26,HoleType.LEFTBOTTOM))
holeList.append(HolePosition(26,10,HoleType.RIGHTTOP))
holeList.append(HolePosition(10,26,HoleType.RIGHTTOP))
holeList.append(HolePosition(-26,10,HoleType.RIGHTBOTTOM))
holeList.append(HolePosition(10,-26,HoleType.LEFTTOP))
holeList.append(HolePosition(26,-10,HoleType.LEFTTOP))
holeList.append(HolePosition(-10,26,HoleType.RIGHTBOTTOM))
holeList.append(HolePosition(-26,-10,HoleType.LEFTBOTTOM))
holeList.append(HolePosition(-10,-26,HoleType.LEFTBOTTOM))
holeList.append(HolePosition(26,11,HoleType.RIGHTTOP))
holeList.append(HolePosition(11,26,HoleType.RIGHTTOP))
holeList.append(HolePosition(-26,11,HoleType.RIGHTBOTTOM))
holeList.append(HolePosition(11,-26,HoleType.LEFTTOP))
holeList.append(HolePosition(26,-11,HoleType.LEFTTOP))
holeList.append(HolePosition(-11,26,HoleType.RIGHTBOTTOM))
holeList.append(HolePosition(-26,-11,HoleType.LEFTBOTTOM))
holeList.append(HolePosition(-11,-26,HoleType.LEFTBOTTOM))
holeList.append(HolePosition(27,0,HoleType.TOP))
holeList.append(HolePosition(0,27,HoleType.TOP))
holeList.append(HolePosition(-27,0,HoleType.BOTTOM))
holeList.append(HolePosition(0,-27,HoleType.BOTTOM))
holeList.append(HolePosition(27,1,HoleType.RIGHTTOP))
holeList.append(HolePosition(1,27,HoleType.RIGHTTOP))
holeList.append(HolePosition(-27,1,HoleType.RIGHTBOTTOM))
holeList.append(HolePosition(1,-27,HoleType.LEFTTOP))
holeList.append(HolePosition(27,-1,HoleType.LEFTTOP))
holeList.append(HolePosition(-1,27,HoleType.RIGHTBOTTOM))
holeList.append(HolePosition(-27,-1,HoleType.LEFTBOTTOM))
holeList.append(HolePosition(-1,-27,HoleType.LEFTBOTTOM))
holeList.append(HolePosition(27,2,HoleType.RIGHTTOP))
holeList.append(HolePosition(2,27,HoleType.RIGHTTOP))
holeList.append(HolePosition(-27,2,HoleType.RIGHTBOTTOM))
holeList.append(HolePosition(2,-27,HoleType.LEFTTOP))
holeList.append(HolePosition(27,-2,HoleType.LEFTTOP))
holeList.append(HolePosition(-2,27,HoleType.RIGHTBOTTOM))
holeList.append(HolePosition(-27,-2,HoleType.LEFTBOTTOM))
holeList.append(HolePosition(-2,-27,HoleType.LEFTBOTTOM))
holeList.append(HolePosition(27,3,HoleType.RIGHTTOP))
holeList.append(HolePosition(3,27,HoleType.RIGHTTOP))
holeList.append(HolePosition(-27,3,HoleType.RIGHTBOTTOM))
holeList.append(HolePosition(3,-27,HoleType.LEFTTOP))
holeList.append(HolePosition(27,-3,HoleType.LEFTTOP))
holeList.append(HolePosition(-3,27,HoleType.RIGHTBOTTOM))
holeList.append(HolePosition(-27,-3,HoleType.LEFTBOTTOM))
holeList.append(HolePosition(-3,-27,HoleType.LEFTBOTTOM))
holeList.append(HolePosition(27,4,HoleType.RIGHTTOP))
holeList.append(HolePosition(4,27,HoleType.RIGHTTOP))
holeList.append(HolePosition(-27,4,HoleType.RIGHTBOTTOM))
holeList.append(HolePosition(4,-27,HoleType.LEFTTOP))
holeList.append(HolePosition(27,-4,HoleType.LEFTTOP))
holeList.append(HolePosition(-4,27,HoleType.RIGHTBOTTOM))
holeList.append(HolePosition(-27,-4,HoleType.LEFTBOTTOM))
holeList.append(HolePosition(-4,-27,HoleType.LEFTBOTTOM))
holeList.append(HolePosition(27,5,HoleType.RIGHTTOP))
holeList.append(HolePosition(5,27,HoleType.RIGHTTOP))
holeList.append(HolePosition(-27,5,HoleType.RIGHTBOTTOM))
holeList.append(HolePosition(5,-27,HoleType.LEFTTOP))
holeList.append(HolePosition(27,-5,HoleType.LEFTTOP))
holeList.append(HolePosition(-5,27,HoleType.RIGHTBOTTOM))
holeList.append(HolePosition(-27,-5,HoleType.LEFTBOTTOM))
holeList.append(HolePosition(-5,-27,HoleType.LEFTBOTTOM))
holeList.append(HolePosition(27,6,HoleType.RIGHTTOP))
holeList.append(HolePosition(6,27,HoleType.RIGHTTOP))
holeList.append(HolePosition(-27,6,HoleType.RIGHTBOTTOM))
holeList.append(HolePosition(6,-27,HoleType.LEFTTOP))
holeList.append(HolePosition(27,-6,HoleType.LEFTTOP))
holeList.append(HolePosition(-6,27,HoleType.RIGHTBOTTOM))
holeList.append(HolePosition(-27,-6,HoleType.LEFTBOTTOM))
holeList.append(HolePosition(-6,-27,HoleType.LEFTBOTTOM))
holeList.append(HolePosition(27,7,HoleType.RIGHTTOP))
holeList.append(HolePosition(7,27,HoleType.RIGHTTOP))
holeList.append(HolePosition(-27,7,HoleType.RIGHTBOTTOM))
holeList.append(HolePosition(7,-27,HoleType.LEFTTOP))
holeList.append(HolePosition(27,-7,HoleType.LEFTTOP))
holeList.append(HolePosition(-7,27,HoleType.RIGHTBOTTOM))
holeList.append(HolePosition(-27,-7,HoleType.LEFTBOTTOM))
holeList.append(HolePosition(-7,-27,HoleType.LEFTBOTTOM))
holeList.append(HolePosition(27,8,HoleType.RIGHTTOP))
holeList.append(HolePosition(8,27,HoleType.RIGHTTOP))
holeList.append(HolePosition(-27,8,HoleType.RIGHTBOTTOM))
holeList.append(HolePosition(8,-27,HoleType.LEFTTOP))
holeList.append(HolePosition(27,-8,HoleType.LEFTTOP))
holeList.append(HolePosition(-8,27,HoleType.RIGHTBOTTOM))
holeList.append(HolePosition(-27,-8,HoleType.LEFTBOTTOM))
holeList.append(HolePosition(-8,-27,HoleType.LEFTBOTTOM))
holeList.append(HolePosition(27,9,HoleType.RIGHTTOP))
holeList.append(HolePosition(9,27,HoleType.RIGHTTOP))
holeList.append(HolePosition(-27,9,HoleType.RIGHTBOTTOM))
holeList.append(HolePosition(9,-27,HoleType.LEFTTOP))
holeList.append(HolePosition(27,-9,HoleType.LEFTTOP))
holeList.append(HolePosition(-9,27,HoleType.RIGHTBOTTOM))
holeList.append(HolePosition(-27,-9,HoleType.LEFTBOTTOM))
holeList.append(HolePosition(-9,-27,HoleType.LEFTBOTTOM))
holeList.append(HolePosition(28,0,HoleType.TOP))
holeList.append(HolePosition(0,28,HoleType.TOP))
holeList.append(HolePosition(-28,0,HoleType.BOTTOM))
holeList.append(HolePosition(0,-28,HoleType.BOTTOM))
holeList.append(HolePosition(28,1,HoleType.RIGHTTOP))
holeList.append(HolePosition(1,28,HoleType.RIGHTTOP))
holeList.append(HolePosition(-28,1,HoleType.RIGHTBOTTOM))
holeList.append(HolePosition(1,-28,HoleType.LEFTTOP))
holeList.append(HolePosition(28,-1,HoleType.LEFTTOP))
holeList.append(HolePosition(-1,28,HoleType.RIGHTBOTTOM))
holeList.append(HolePosition(-28,-1,HoleType.LEFTBOTTOM))
holeList.append(HolePosition(-1,-28,HoleType.LEFTBOTTOM))
holeList.append(HolePosition(28,2,HoleType.RIGHTTOP))
holeList.append(HolePosition(2,28,HoleType.RIGHTTOP))
holeList.append(HolePosition(-28,2,HoleType.RIGHTBOTTOM))
holeList.append(HolePosition(2,-28,HoleType.LEFTTOP))
holeList.append(HolePosition(28,-2,HoleType.LEFTTOP))
holeList.append(HolePosition(-2,28,HoleType.RIGHTBOTTOM))
holeList.append(HolePosition(-28,-2,HoleType.LEFTBOTTOM))
holeList.append(HolePosition(-2,-28,HoleType.LEFTBOTTOM))
holeList.append(HolePosition(28,3,HoleType.RIGHTTOP))
holeList.append(HolePosition(3,28,HoleType.RIGHTTOP))
holeList.append(HolePosition(-28,3,HoleType.RIGHTBOTTOM))
holeList.append(HolePosition(3,-28,HoleType.LEFTTOP))
holeList.append(HolePosition(28,-3,HoleType.LEFTTOP))
holeList.append(HolePosition(-3,28,HoleType.RIGHTBOTTOM))
holeList.append(HolePosition(-28,-3,HoleType.LEFTBOTTOM))
holeList.append(HolePosition(-3,-28,HoleType.LEFTBOTTOM))
holeList.append(HolePosition(28,4,HoleType.RIGHTTOP))
holeList.append(HolePosition(4,28,HoleType.RIGHTTOP))
holeList.append(HolePosition(-28,4,HoleType.RIGHTBOTTOM))
holeList.append(HolePosition(4,-28,HoleType.LEFTTOP))
holeList.append(HolePosition(28,-4,HoleType.LEFTTOP))
holeList.append(HolePosition(-4,28,HoleType.RIGHTBOTTOM))
holeList.append(HolePosition(-28,-4,HoleType.LEFTBOTTOM))
holeList.append(HolePosition(-4,-28,HoleType.LEFTBOTTOM))
holeList.append(HolePosition(28,5,HoleType.RIGHTTOP))
holeList.append(HolePosition(5,28,HoleType.RIGHTTOP))
holeList.append(HolePosition(-28,5,HoleType.RIGHTBOTTOM))
holeList.append(HolePosition(5,-28,HoleType.LEFTTOP))
holeList.append(HolePosition(28,-5,HoleType.LEFTTOP))
holeList.append(HolePosition(-5,28,HoleType.RIGHTBOTTOM))
holeList.append(HolePosition(-28,-5,HoleType.LEFTBOTTOM))
holeList.append(HolePosition(-5,-28,HoleType.LEFTBOTTOM))

paintHolePlane(createSketch(1),basicHoleDefinition,holeList)

#document.getObject('Pad').Visibility = False
olePosition(-1.03,-27.81,HoleType.LEFTBOTTOM))
holeList.append(HolePosition(27.81,2.06,HoleType.RIGHTTOP))
holeList.append(HolePosition(2.06,27.81,HoleType.RIGHTTOP))
holeList.append(HolePosition(-27.81,2.06,HoleType.RIGHTBOTTOM))
holeList.append(HolePosition(2.06,-27.81,HoleType.LEFTTOP))
holeList.append(HolePosition(27.81,-2.06,HoleType.LEFTTOP))
holeList.append(HolePosition(-2.06,27.81,HoleType.RIGHTBOTTOM))
holeList.append(HolePosition(-27.81,-2.06,HoleType.LEFTBOTTOM))
holeList.append(HolePosition(-2.06,-27.81,HoleType.LEFTBOTTOM))
holeList.append(HolePosition(27.81,3.09,HoleType.RIGHTTOP))
holeList.append(HolePosition(3.09,27.81,HoleType.RIGHTTOP))
holeList.append(HolePosition(-27.81,3.09,HoleType.RIGHTBOTTOM))
holeList.append(HolePosition(3.09,-27.81,HoleType.LEFTTOP))
holeList.append(HolePosition(27.81,-3.09,HoleType.LEFTTOP))
holeList.append(HolePosition(-3.09,27.81,HoleType.RIGHTBOTTOM))
holeList.append(HolePosition(-27.81,-3.09,HoleType.LEFTBOTTOM))
holeList.append(HolePosition(-3.09,-27.81,HoleType.LEFTBOTTOM))
holeList.append(HolePosition(27.81,4.12,HoleType.RIGHTTOP))
holeList.append(HolePosition(4.12,27.81,HoleType.RIGHTTOP))
holeList.append(HolePosition(-27.81,4.12,HoleType.RIGHTBOTTOM))
holeList.append(HolePosition(4.12,-27.81,HoleType.LEFTTOP))
holeList.append(HolePosition(27.81,-4.12,HoleType.LEFTTOP))
holeList.append(HolePosition(-4.12,27.81,HoleType.RIGHTBOTTOM))
holeList.append(HolePosition(-27.81,-4.12,HoleType.LEFTBOTTOM))
holeList.append(HolePosition(-4.12,-27.81,HoleType.LEFTBOTTOM))

paintHolePlane(createSketch(1),basicHoleDefinition,holeList)

#document.getObject('Pad').Visibility = False
